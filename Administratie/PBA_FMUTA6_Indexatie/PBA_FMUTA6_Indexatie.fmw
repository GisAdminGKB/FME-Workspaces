FME workspace PBA_FMUTA6_Indexatie.fmw
Title: PBA_FMUTA6_Conversie
Description: PBA_FMUTA6_Conversie
Deze workspace converteert een PBA factuur export naar het FMUTA6 formaat.
Input is een excel bestand met alle factuurregels uit PBA en de output is een CSV bestand met 2 regels per factuur.

Parameters:
- ResultaatEmail = anita@grondbankijsselmonde.nl   # Resultaat emailen naar
- _zone_timestamp:
      from datetime import datetime
      from zoneinfo import ZoneInfo
      
      return datetime.now(ZoneInfo("Europe/Amsterdam")).strftime('%Y%m%d%H%M%S')
- Factuur_XLSX = C:\Users\dirkjan\OneDrive - GKB Groep\Projecten Realisatie\GKBY\FMUTA_Indexatie\Melding 5-5-2026\Factuurrun 2262144.xlsx   # PBA Factuurrunbestand (.xlsx)
- Bonnen_XLSX = C:\Users\dirkjan\OneDrive - GKB Groep\Projecten Realisatie\GKBY\FMUTA_Indexatie\Melding 5-5-2026\Bonnen 01-01-2026 tm 22-04-2026.xlsx   # PBA Bonnenoverzicht (.xlsx)
- GKB_BEDRIJVEN = 1,8,215,327,1532,1698
- RDAM_BEDRIJVEN = 443,1136,1139,1155,1156,1157,1158,1159,1161,1162,1444,1463,1478
- FME_SHAREDRESOURCE_DATA = c:\temp   # FME Flow Data Directory
- FME_SHAREDRESOURCE_TEMP = c:\temp   # FME Flow Temporary Resource Directory

Junction_17
    -> FeatureReader_bonregels [INITIATOR]
    -> FeatureReader_Factuurregels [INITIATOR]
Junction_5
Note: Documentatie v7: / Gebaseerd op de laatste productie versie 6. / Naar aanleiding van missende waarden in de CSV output een revisie van v6 gemaakt. Door de hele workspace heen gekropen gedocumenteerd en logica verbeterd. / Fout in statistike opgelost met totaalBTW weergave. / Log wordt nu ook weggeschreven in html page en naar factuurrun folder gekopieerd. / Sortering log aangepast / 07-05-2026 / - Afrondingsverschillen geminimaliseerd door de eerste overbodige roudings eruit te halen / - De indexatieregels opsplitsen per week omdat per week er andere tarieven (kunnen) zijn.
Note: EXCEL_LOG_WRITER : Instellingen
Junction_27
    -> Junction_28
Note: AttributeCreator_url_paden : Output
Junction_28
    -> EXCEL_LOG_WRITER [Output]
Junction_16
    -> HTTPCaller_2
    -> HTTPCaller
    -> FeatureReader_FMUTA6_Schema [INITIATOR]
    -> HTTPCaller_IW_DataConnector
Note: AttributeCreator_indexatie : Output
Junction_30
    -> EXCEL_LOG_WRITER [Output01]
Note: StatisticsCalculator_2 : Summary
Junction_26
    -> EXCEL_LOG_WRITER [Summary]
Note: AttributeCreator_CSVBestand : Output
Junction_24
    -> EXCEL_LOG_WRITER [Output00]

Bookmark: Init parameters
Creator
    GEOMTYPE = Geometry Object
    NUM = 1
    CREATED -> AttributeCreator_url_paden
AttributeCreator_url_paden
    ATTR_TABLE:
      SET_TO data_dir (varchar(200)) = FME_CONDITIONAL:DEFAULT_VALUE'$(FME_SHAREDRESOURCE_DATA)Grondbank/FMUTA6'BOOL_OP;OR;COMPOSITE_TEST;1;TEST $(FME_OS) = Windows'$(FME_SHAREDRESOURCE_DATA)\Grondbank\FMUTA6'FME_NUM_CONDITIONS2___
      SET_TO IndexatieBestand (varchar(200)) = @Value(data_dir)\GBY_Indexatie.xlsx
      SET_TO LogBestand (varchar(200)) = @Value(data_dir)\Log\Log_run_$(_zone_timestamp).xlsx
      SET_TO CSV_Schema (varchar(200)) = @Value(data_dir)\FMUTA6_Schema.csv
      SET_TO _url_IW_DataConnector (varchar(73)) = https://infraworks.gkbgroep.nl/Dataconnector/v1/beta/PieterBas/Debiteuren
      SET_TO Startdatum (varchar(10)) = 16-03-2026
      SET_TO _url_get_artikelen (varchar(80)) = https://fme-gkb.fmecloud.com/api/IndexatieGrondbank/indexatie_artikelen?DEBUG=NO
      SET_TO _url_get_indexaties (varchar(71)) = https://fme-gkb.fmecloud.com/api/IndexatieGrondbank/indexaties?DEBUG=NO
      SET_TO _token_indexatie_API (varchar(41)) = c8fe3945982941066a1c4964d8a2ca5759e86c2b
      SET_TO CSVBestand (varchar(200)) = PB_Factuur_FMUTA6_$(_zone_timestamp)
      SET_TO destination_dir (varchar(200)) = FME_CONDITIONAL:DEFAULT_VALUE'@Value(data_dir)/Factuurrun_@Value(CSVBestand)'BOOL_OP;OR;COMPOSITE_TEST;1;TEST $(FME_OS) = Windows'@Value(data_dir)\Factuurrun_@Value(CSVBestand)'FME_NUM_CONDITIONS2___
    INPUT_PORT_CONNECTED = CONNECTED
    -> Junction_17
    -> Junction_16
    -> Sampler
    -> Junction_27

Bookmark: NIEUWE Brondata 2 bestanden samenvoegen
FeatureReader_Factuurregels
    ATTRIBUTES = Factuur,"Factuurrun.code,Factuurrun.Omschrijving,""Factuur nummer"",""Factuur datum"",Vervaldatum,Relatie.Code,Relatie.Omschrijving,Relatie.Adres.Straat,Relatie.Adres.Huisnummer,Relatie.Adres.Toevoeging,Relatie.Adres.Postcode,Relatie.Adres.Plaats,Relatie.Adres.Land.Code,Relatie.Adres.Land.Omschrijving,FactuurRegel.Bon.Code,FactuurRegel.Bon.Datum,FactuurRegel.Artikel.Code,FactuurRegel.Artikel.Omschrijving,FactuurRegel.Opbrengst.Code,FactuurRegel.Opbrengst.Omschrijving,FactuurRegel.Hoeveelheid,FactuurRegel.Eenheid,FactuurRegel.Tarief,FactuurRegel.Percentage,""FactuurRegel.Bedrag excl. Btw"",""FactuurRegel.Bedrag Btw"",FactuurRegel.Vestiging.Code,FactuurRegel.Vestiging.Omschrijving,""FactuurRegel.Factuur groep.Code"",""FactuurRegel.Factuur groep.Omschrijving"",FactuurRegel.Administratie.Code,FactuurRegel.Administratie.Omschrijving,""FactuurRegel.Correctie factuur.Code"""
    ATTR_ACCUM_MODE = Merge Initiator and Result
    ATTR_CONFLICT_RES = Use Result
    ATTR_IGNORE_NULLS = No
    CLIP_TO_ENVELOPE = NO
    COMBINE_GEOM = Use Result
    DATASET = $(Factuur_XLSX)
    FEATURETYPES = Factuur
    FORMAT = XLSXR
    INITIATOR_FIRST_OUTPUT = default
    INPUT_PORT_INITIATOR_CONNECTED = CONNECTED
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    XLSXR_ALLOW_DOLLAR_SIGNS = YES
    XLSXR_APPLY_FILTERS = No
    XLSXR_CASE_SENSITIVE_FEATURE_TYPES = YES
    XLSXR_CREATE_FEATURE_TABLES_FROM_DATA = Yes
    XLSXR_EXCEL_COL_NAMES = YES
    XLSXR_EXPANDED_DATES_SCANNING = No
    XLSXR_EXPAND_MERGED_CELLS = Yes
    XLSXR_FORCE_DATETIME = NO
    XLSXR_QUERY_FEATURE_TYPES_FOR_MERGE_FILTERS = Yes
    XLSXR_READ_BLANK_AS = Null
    XLSXR_READ_FORM_CONTROLS = NONE
    XLSXR_READ_RASTER_MODE = None
    XLSXR_REPLACE_ONLY_NEWLINES_CARRIAGE_RETURNS = YES
    XLSXR_SCAN_FOR_GEOMETRIC_TYPES = Yes
    XLSXR_SCAN_MAX_FEATURES = 1000
    XLSXR_SCHEMA_HANDLING_REVISION = 2
    XLSXR_SKIP_EMPTY_ATTRS = No
    XLSXR_SKIP_EMPTY_ROWS = YES
    XLSXR_STRIP_SHEETNAME_SPACES = YES
    XLSXR_TRIM_ATTR_NAME_WHITESPACE = Yes
    XLSXR_USE_CUSTOM_SCHEMA = NO
    Factuur -> TestFilter_Bedrijven
TestFilter_Bedrijven
    DEFAULT_VALUE = Verwerken
    OUTPUT_ATTRIBUTE_NAME = Verwerken
    PASSED_TEST_GROUP_OUTPUT = FIRST
    TEST_LIST = "BOOL_OP,OR,COMPOSITE_TEST,""""""1"""""",TEST_CLAUSE,TEST @Value(Relatie.Code) IN $(RDAM_BEDRIJVEN)",RDAM Bedrijf,"BOOL_OP,OR,COMPOSITE_TEST,""""""1"""""",TEST_CLAUSE,TEST @Value(Relatie.Code) IN $(GKB_BEDRIJVEN)",GKB Bedrijf
    RDAM Bedrijf -> Junction_5
    GKB Bedrijf -> TestFilte_boncode_gevuld
    GKB Bedrijf -> TestFilter_factuurdatum
    Verwerken -> TestFilter_factuurdatum
TestFilter_factuurdatum
    DEFAULT_VALUE = Lege factuurdatum
    PASSED_TEST_GROUP_OUTPUT = FIRST
    TEST_LIST = "BOOL_OP,OR,COMPOSITE_TEST,""""""1"""""",TEST_CLAUSE,TEST Factuur datum ATTRIBUTE_HAS_A_VALUE """,Factuur datum ATTRIBUTE_HAS_A_VALUE
    Factuur datum ATTRIBUTE_HAS_A_VALUE -> AttributeKeeper_factuurregels
    Lege factuurdatum -> AttributeKeeper_8
AttributeKeeper_factuurregels
    CREATE_BULK_MODE_FEATURES = NO
    KEEP_ATTRS = CSV_Schema,Factuur datum,Factuur nummer,FactuurRegel.Artikel.Code,FactuurRegel.Artikel.Omschrijving,FactuurRegel.Bedrag Btw,FactuurRegel.Bedrag excl. Btw,FactuurRegel.Bon.Code,FactuurRegel.Bon.Datum,FactuurRegel.Eenheid,FactuurRegel.Hoeveelheid,FactuurRegel.Tarief,Factuurrun.Omschrijving,Factuurrun.code,IndexatieBestand,Relatie.Code,Relatie.Omschrijving,Startdatum,Vervaldatum,_creation_instance,_url_IW_DataConnector,data_dir,Relatie.Adres.Toevoeging
    -> FeatureMerger_facturen_bonnen [REQUESTOR]
FeatureReader_bonregels
    ATTRIBUTES = Voorraad,"Code,Code1,Datum,Tijd,Referentie,Inweegtijd,Status,Kenteken,Transporteur.Code,Transporteur.Omschrijving,Transporteur.Adres.Straat,Transporteur.Adres.Huisnummer,Transporteur.Adres.Toevoeging,Transporteur.Adres.Postcode,Transporteur.Adres.Plaats,Transporteur.Adres.Land.Code,Transporteur.Adres.Land.Omschrijving,Transporteur.Relatiegroep.Code,Transporteur.Relatiegroep.Omschrijving,Klant.Code,Klant.Omschrijving,Klant.Adres.Straat,Klant.Adres.Huisnummer,Klant.Adres.Toevoeging,Klant.Adres.Postcode,Klant.Adres.Plaats,Klant.Adres.Land.Code,Klant.Adres.Land.Omschrijving,Klant.Relatiegroep.Code,Klant.Relatiegroep.Omschrijving,Rekeningnemer.Code,Rekeningnemer.Omschrijving,Rekeningnemer.Adres.Straat,Rekeningnemer.Adres.Huisnummer,Rekeningnemer.Adres.Toevoeging,Rekeningnemer.Adres.Postcode,Rekeningnemer.Adres.Plaats,Rekeningnemer.Adres.Land.Code,Rekeningnemer.Adres.Land.Omschrijving,Rekeningnemer.Relatiegroep.Code,Rekeningnemer.Relatiegroep.Omschrijving,Contract.Code,Contract.Omschrijving,Werklocatie.Code,Werklocatie.Omschrijving,Vestiging.Code,Vestiging.Omschrijving,Partikulier_Naam,Partikulier_Adres,Partikulier_Huisnummer,Partikulier_Toevoeging,Partikulier_Postcode,Partikulier_Plaats,Partikulier_Land.Code,Partikulier_Land.Omschrijving,Partikulier_Telefoon,Ingaand,Artikel.Code,Artikel.Omschrijving,Artikel.Eural.Code,Artikel.Eural.Omschrijving,Artikel.GN_Code,Lokatie.Code,Lokatie.Omschrijving,Partij.Code,Partij.Omschrijving,AMVBstroom.Code,AMVBstroom.Omschrijving,AMVBstroom.Eural.Code,AMVBstroom.Eural.Omschrijving,Vergunning.Code,Vergunning.Omschrijving,Geleidebiljet,Container.Code,Container.Omschrijving,""Hoeveelheid ingaand"",""Hoeveelheid uitgaand"",Eenheid,Gecorrigeerd/tegenboeking,""Correctie weegbon"""
    ATTR_ACCUM_MODE = Only Use Result
    CLIP_TO_ENVELOPE = NO
    COMBINE_GEOM = Use Result
    DATASET = $(Bonnen_XLSX)
    FEATURETYPES = Voorraad
    FORMAT = XLSXR
    INITIATOR_FIRST_OUTPUT = default
    INPUT_PORT_INITIATOR_CONNECTED = CONNECTED
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    XLSXR_ALLOW_DOLLAR_SIGNS = YES
    XLSXR_APPLY_FILTERS = No
    XLSXR_CASE_SENSITIVE_FEATURE_TYPES = YES
    XLSXR_CREATE_FEATURE_TABLES_FROM_DATA = Yes
    XLSXR_EXCEL_COL_NAMES = YES
    XLSXR_EXPANDED_DATES_SCANNING = No
    XLSXR_EXPAND_MERGED_CELLS = Yes
    XLSXR_FORCE_DATETIME = NO
    XLSXR_QUERY_FEATURE_TYPES_FOR_MERGE_FILTERS = Yes
    XLSXR_READ_BLANK_AS = Null
    XLSXR_READ_FORM_CONTROLS = NONE
    XLSXR_READ_RASTER_MODE = None
    XLSXR_REPLACE_ONLY_NEWLINES_CARRIAGE_RETURNS = YES
    XLSXR_SCAN_FOR_GEOMETRIC_TYPES = Yes
    XLSXR_SCAN_MAX_FEATURES = 1000
    XLSXR_SCHEMA_HANDLING_REVISION = 2
    XLSXR_SKIP_EMPTY_ATTRS = No
    XLSXR_SKIP_EMPTY_ROWS = YES
    XLSXR_STRIP_SHEETNAME_SPACES = YES
    XLSXR_TRIM_ATTR_NAME_WHITESPACE = Yes
    XLSXR_USE_CUSTOM_SCHEMA = NO
    Voorraad -> AttributeKeeper_bonregels
    Voorraad -> Sorter_op_boncode
AttributeKeeper_bonregels
    CREATE_BULK_MODE_FEATURES = NO
    KEEP_ATTRS = Artikel.Code,Artikel.Omschrijving,Contract.Code,Contract.Omschrijving,Referentie,Code,Werklocatie.Omschrijving,Gecorrigeerd/tegenboeking,Datum,Kenteken,Werklocatie.Code
    -> TestFilter_bonregels
TestFilter_bonregels
    DEFAULT_VALUE = Geldige regels
    PASSED_TEST_GROUP_OUTPUT = FIRST
    TEST_LIST = "BOOL_OP,OR,COMPOSITE_TEST,""""""1"""""",TEST_CLAUSE,TEST @Value(Gecorrigeerd/tegenboeking) = Ja",Is correctie regel
    Is correctie regel -> FeatureMerger_facturen_bonnen [SUPPLIER]
    Geldige regels -> FeatureMerger_facturen_bonnen [SUPPLIER]
FeatureMerger_facturen_bonnen
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(FactuurRegel.Bon.Code) @Value(Code) AUTO @Value(FactuurRegel.Artikel.Code) @Value(Artikel.Code) AUTO
    MERGE_TYPE_VAL = ATTRIBUTES
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGE_TYPE = Attributes Only
    MERGED -> AttributeExposer_FMUTA6_Schema
    MERGED -> Junction_21
    UNMERGED_REQUESTOR -> Junction_12
AttributeExposer_FMUTA6_Schema
    ATTR_TABLE = Bedrag,real32,"BTW bedrag regel",real32,BTWsoort,uint32,Dagboekcode,varchar(1),Dagboeknummer,varchar(1),Debiteurnummer,uint32,Factuurdatum,date,Factuuregelomschrijving,varchar(200),Factuurnummer,varchar(50),Grootboekrekening,uint32,"nvt (1)",varchar(1),Aantal,real32,Eenheid,varchar(10),Tarief,real32,Artikelomschrijving,varchar(200),"nvt (6)",varchar(1),Periode,uint32,Referentie,varchar(1),Regelnummer,uint32,Valuta,varchar(3),"Vervaldatum factuur",date,"Vervaldatum KB",date
    -> PythonCaller_ISO_weeknummers
Note: Rapportage debiteuren controle
Junction_21
    -> Junction_22
Note: Rapportage_missende_bonnen
Junction_12
    -> Junction_13

Bookmark: Raportage lege factuuratums, runs niet geconverteerd
AttributeKeeper_8
    CREATE_BULK_MODE_FEATURES = NO
    KEEP_ATTRS = Factuur nummer,Factuurrun.code,Relatie.Code,Relatie.Omschrijving
    -> FeatureCounter
FeatureCounter
    FeatureCounterNewAttrParameter = _aantal_lege_factuurdatum
    GroupBox = NO
    -> AttributeCreator_html_13
AttributeCreator_html_13
    ATTR_TABLE:
      SET_TO html_facturen (varchar(200)) =       <tr>
                 <td>@Value(Factuurrun.code)</td>
                 <td>@Value(Factuur nummer)</td>
                 <td>@Value(Relatie.Code)</td>
                 <td>@Value(Relatie.Omschrijving)</td>
              </tr>
    -> AttributeCombiner_6
AttributeCombiner_6
    ATTRS = html_facturen
    DROP_EMPTY = No
    QUOT = None
    -> AttributeCreator_html_14
AttributeCreator_html_14
    ATTR_TABLE:
      SET_TO html_content (varchar(200)) = <h4>Deze <font color=red>@Value(_aantal_lege_factuurdatum)</font> factuurruns hebben een lege factuurdatum (niet definitief in PB)</h4>
        <font color=red>Let op: Deze factuurruns zijn niet meegenomen in de conversie naar IW !</font>
        <table border=1>
           <thead>
              <tr>
                 <th>Factuurrun</th>
                 <th>Faactuurnummer</th>
                 <th>Relatiecode</th>
                 <th>Relatienaam</th>
              </tr>
           </thead>
           <tbody>
        @Value(html_facturen)
           </tbody>
        </table>

      SET_TO Volgorde (uint8) = 3
    -> Junction_4

Bookmark: Bewerk factuurdata
TestFilte_boncode_gevuld: TestFilter
    DEFAULT_VALUE = <UNFILTERED>
    PASSED_TEST_GROUP_OUTPUT = FIRST
    TEST_LIST = "BOOL_OP,OR,COMPOSITE_TEST,""""""1"""""",TEST_CLAUSE,TEST FactuurRegel.Bon.Code ATTRIBUTE_HAS_A_VALUE """,Code is gevuld
    Code is gevuld -> AttributeManager_veldnamen_2
AttributeManager_veldnamen_2
    ATTR_TABLE:
      RENAME_SET_VALUE FactuurRegel.Bon.Code > Onvangstbonnr (varchar(8))
      RENAME_SET_VALUE FactuurRegel.Bon.Datum > Ontvangstdatum (varchar(10))
      SET_TO Artikelnr (varchar(14)) = FME_NULL_VALUE
      RENAME_SET_VALUE FactuurRegel.Artikel.Omschrijving > Artikelomschrijving (varchar(34))
      RENAME_SET_VALUE FactuurRegel.Hoeveelheid > Aantal (number(6,3))
      RENAME_SET_VALUE FactuurRegel.Eenheid > Eenheid (varchar(10))
      RENAME_SET_VALUE FactuurRegel.Tarief > Prijs (number(6,2))
      RENAME_SET_VALUE FactuurRegel.Percentage > BTW (int16) = FME_CONDITIONAL:DEFAULT_VALUE'V'BOOL_OP;OR;COMPOSITE_TEST;1;TEST @Value(BTW) = 21'H'BOOL_OP;OR;COMPOSITE_TEST;1;TEST @Value(BTW) = 9'L'BOOL_OP;OR;COMPOSITE_TEST;1;TEST @Value(BTW) = 0'N'FME_NUM_CONDITIONS4___
      REMOVE Factuurrun.code (varchar(9))
      REMOVE Factuurrun.Omschrijving (varchar(20))
      REMOVE Factuur nummer (int32)
      REMOVE Factuur datum (date)
      REMOVE Vervaldatum (date)
      REMOVE Relatie.Adres.Straat (varchar(24))
      REMOVE Relatie.Adres.Huisnummer (int32)
      REMOVE Relatie.Adres.Toevoeging (varchar(1))
      REMOVE Relatie.Adres.Postcode (varchar(7))
      REMOVE Relatie.Adres.Plaats (varchar(24))
      REMOVE Relatie.Adres.Land.Code (varchar(2))
      REMOVE Relatie.Adres.Land.Omschrijving (varchar(9))
      REMOVE FactuurRegel.Artikel.Code (varchar(5))
      REMOVE FactuurRegel.Opbrengst.Code (int16)
      REMOVE FactuurRegel.Opbrengst.Omschrijving (varchar(21))
      REMOVE FactuurRegel.Bedrag excl. Btw (number(7,2))
      REMOVE FactuurRegel.Bedrag Btw (number(6,2))
      REMOVE FactuurRegel.Vestiging.Code (int16)
      REMOVE FactuurRegel.Vestiging.Omschrijving (varchar(30))
      REMOVE FactuurRegel.Factuur groep.Code (int16)
      REMOVE FactuurRegel.Factuur groep.Omschrijving (varchar(13))
      REMOVE FactuurRegel.Administratie.Code (int16)
      REMOVE FactuurRegel.Administratie.Omschrijving (varchar(34))
      REMOVE FactuurRegel.Correctie factuur.Code (varchar(1))
    -> FeatureMerger_bondata_aan_factuurregels_koppelen [REQUESTOR]
    -> Junction_19
Note: StatisticsCalculator : Input
Junction_19
    -> Junction_20

Bookmark: Statistiek voor logging
Junction_20
    -> StatisticsCalculator_5
StatisticsCalculator_5
    ATTR_ACCUM_MODE = None
    CALCULATION_MODE = NUMERIC
    FEAT_STATS = Onvangstbonnr,NUMERIC_MODE,,,COUNT,,,,,,,,,,
    GROUP_BY = Relatie.Code Relatie.Omschrijving
    SUMMARY -> AttributeManager_2
AttributeManager_2
    ATTR_TABLE:
      RENAME_SET_VALUE Onvangstbonnr.total_count > FactuurregelsTotaal (uint64)
      RENAME_SET_VALUE Relatie.Code > DebiteurCode (int16)
      RENAME_SET_VALUE Relatie.Omschrijving > DebiteurNaam (varchar(41))
    -> FeatureMerger_6 [REQUESTOR]
Junction_18
    -> StatisticsCalculator_6
StatisticsCalculator_6
    ATTR_ACCUM_MODE = None
    CALCULATION_MODE = NUMERIC
    FEAT_STATS = Onvangstbonnr,NUMERIC_MODE,,,COUNT,,,,,,,,,,
    GROUP_BY = Relatie.Code Relatie.Omschrijving
    SUMMARY -> AttributeManager_8
AttributeManager_8
    ATTR_TABLE:
      RENAME_SET_VALUE Onvangstbonnr.total_count > MatchedTotaal (uint64)
      RENAME_SET_VALUE Relatie.Code > DebiteurCode (int16)
      RENAME_SET_VALUE Relatie.Omschrijving > DebiteurNaam (varchar(41))
    -> FeatureMerger_6 [SUPPLIER]
FeatureMerger_6
    ATTR_ACCUM_MODE = Merge Supplier
    ATTR_CONFLICT_RES_LOOKUP = REQUESTOR_IF_CONFLICT
    IGNORE_NULLS = No
    JOIN_KEYS = @Value(DebiteurCode) @Value(DebiteurCode) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> Sorter_2
Sorter_2
    SORT_PARM = DebiteurCode NATURAL ASCENDING NON_VALUES_AFTER_VALUES
    SORTED -> AttributeCreator_html_16
AttributeCreator_html_16
    ATTR_TABLE:
      SET_TO NietVerwerkteRegels (real64) = @Evaluate(@Value(FactuurregelsTotaal) - @Value(MatchedTotaal))
      SET_TO html_content (varchar(200)) =             <tr>
                       <td>@Value(DebiteurCode)</td>
                       <td>@Value(DebiteurNaam)</td>
                        <td>@Value(FactuurregelsTotaal)</td>
                        <td>@Value(MatchedTotaal)</td>
                        <td><font color=red>@Value(NietVerwerkteRegels)</font></td>
                    </tr>
    -> AttributeCombiner_8
AttributeCombiner_8
    ATTRS = html_content
    DROP_EMPTY = No
    QUOT = None
    -> AttributeCreator_html_17
AttributeCreator_html_17
    ATTR_TABLE:
      SET_TO html_content (varchar(200)) = <h4>Ontvangstregels per GKB Bedrijf</h4>
        <table border=1>
           <thead>
              <tr>
                 <th>Debiteur</th>
                 <th>Naam</th>
                 <th>Factuurregels totaal</th>
                 <th>Factuurregels verwerkt</th>
                 <th>Factuurregels onverwerkt</th>
              </tr>
           </thead>
           <tbody>
        @Value(html_content)
           </tbody>
        </table>


      SET_TO Volgorde (uint8) = 111
    -> FeatureMerger_5 [SUPPLIER]

Bookmark: Subregels maken
PythonCaller_ISO_weeknummers
    INPUT_PORT_CONNECTED = CONNECTED
    NEW_ATTRIBUTES = _bon_week buffer _start_week buffer _interval_week buffer
    PYTHONSOURCE:
      import fme
      from fme import BaseTransformer
      import fmeobjects
      import datetime
      from datetime import date


      class FeatureProcessor(BaseTransformer):
          """Template Class Interface:
          When using this class, make sure its name is set as the value of the 'Class to Process Features'
          transformer parameter.

          This class inherits from 'fme.BaseTransformer'. For full details of this class, its methods, and
          expected usage, see https://docs.safe.com/fme/html/fmepython/api/fme.html#fme.BaseTransformer.
          """

          def __init__(self):
              """Base constructor for class members."""
              pass

          def has_support_for(self, support_type: int):
              """This method is called by FME to determine if the PythonCaller supports Bulk mode,
              which allows for significant performance gains when processing large numbers of features.
              """
              return support_type == fmeobjects.FME_SUPPORT_FEATURE_TABLE_SHIM

          def input(self, feature: fmeobjects.FMEFeature):
              """This method is called for each feature which enters the PythonCaller."""
              Startdatum = feature.getAttribute('Startdatum')
              Bondatum = feature.getAttribute('FactuurRegel.Bon.Datum')
              # Assuming format YYYY-MM-DD
              #_bondatum = datetime.datetime.strptime(Bondatum, '%Y%m%d')
              _bondatum = datetime.datetime.strptime(Bondatum, '%d-%m-%Y')
              _startdatum = datetime.datetime.strptime(Startdatum, '%d-%m-%Y')
              # returns (ISOyear, ISOweek, ISOweekday)
              bonyear, bonweek, bonweekday = _bondatum.isocalendar()
              startyear, startweek, startweekday = _startdatum.isocalendar()
              feature.setAttribute('_bon_week', bonweek)
              feature.setAttribute('_start_week', startweek)
              feature.setAttribute('_interval_week', bonweek - startweek)
              self.pyoutput(feature, output_tag="PYOUTPUT")

          def close(self):
              """This method is called once all the FME Features have been processed from input()."""
              pass

          def process_group(self):
              """This method is called by FME for each group when group processing mode is enabled."""
              pass

          def reject_feature(self, feature: fmeobjects.FMEFeature, code: str, message: str):
              """This method can be used to output a feature to the <Rejected> port."""
              feature.setAttribute("fme_rejection_code", code)
              feature.setAttribute("fme_rejection_message", message)
              self.pyoutput(feature, output_tag="<Rejected>")
    PYTHONSYMBOL = FeatureProcessor
    -> TestFilter
    -> Merger_contractfactuurnummers_aan_factuurregels [REQUESTOR]
Note: EXCEL_LOG_WRITER : CALC_INDEXATIE
AttributeManager_subregels_algemeen
    ATTR_TABLE:
      SET_TO Factuur nummer (int32) = FME_CONDITIONAL:DEFAULT_VALUE'_FME_NO_OP_'BOOL_OP;AND;COMPOSITE_TEST;1 AND 2;TEST _factuurnummer_contract NOT_ATTRIBUTE_IS_MISSING _FME_BLANK_STRING_;TEST _factuurnummer_contract ATTRIBUTE_HAS_A_VALUE _FME_BLANK_STRING_'@Value(_factuurnummer_contract)'FME_NUM_CONDITIONS2___
      SET_TO Bedrag (real32)
      SET_TO BTWsoort (varchar(14)) = 15009
      SET_TO Dagboekcode (varchar(14)) = FME_NULL_VALUE
      SET_TO Dagboeknummer (varchar(14)) = FME_NULL_VALUE
      SET_TO Debiteurnummer (varchar(14)) = FME_NULL_VALUE
      SET_TO Factuurdatum (date) = @DateTimeFormat(@Value(Factuur datum),%d%m%Y)
      SET_TO Factuuregelomschrijving (varchar(200)) = @Value(FactuurRegel.Artikel.Omschrijving)
      SET_TO Factuurnummer (varchar(50)) = @Value(Factuur nummer)""
      SET_TO Grootboekrekening (varchar(14)) = 80120
      SET_TO nvt (1) (varchar(14)) = FME_NULL_VALUE
      SET_TO nvt (6) (varchar(14)) = FME_NULL_VALUE
      SET_TO Periode (varchar(14)) = FME_NULL_VALUE
      SET_TO Regelnummer (uint32) = 1
      SET_TO Valuta (varchar(3)) = EUR
      SET_TO Vervaldatum factuur (varchar(14)) = FME_NULL_VALUE
      SET_TO Vervaldatum KB (varchar(14)) = FME_NULL_VALUE
      SET_TO Aantal (real32) = @Value(FactuurRegel.Hoeveelheid)
      SET_TO Eenheid (varchar(10)) = @Value(FactuurRegel.Eenheid)
      SET_TO Tarief (real32) = @Value(FactuurRegel.Tarief)
      SET_TO Artikelomschrijving (varchar(3)) = @Value(FactuurRegel.Bon.Code)
    -> FeatureMerger_productgroep [REQUESTOR]
AttributeRounder_4
    PLACES = 2
    ROUND_TYPE_TCL = round
    SRC_ATTRS = BTW bedrag regel Bedrag IndexatieBedragBTW IndexatieBedragBTW.sum IndexatieBedragExBTW IndexatieBedragExBTW.sum IndexatieTarief
    ROUND_TYPE = Nearest
    -> Sorter_subregels
Sorter_subregels
    SORT_PARM = Factuur nummer NATURAL ASCENDING NON_VALUES_AFTER_VALUES _regelnummer_factuur NATURAL ASCENDING NON_VALUES_AFTER_VALUES
    SORTED -> AttributeKeeper_subregel
    SORTED -> Junction
Note: StatisticsCalculator_bedragen_en_regels_per_factuur_2 : Input
Junction
    -> Junction_8
AttributeKeeper_subregel
    CREATE_BULK_MODE_FEATURES = NO
    KEEP_ATTRS = BTW bedrag regel,BTWsoort,Bedrag,Dagboekcode,Dagboeknummer,Debiteurnummer,Factuurdatum,Factuuregelomschrijving,Factuurnummer,Grootboekrekening,Periode,Referentie,Regelnummer,Valuta,Vervaldatum KB,Vervaldatum factuur,nvt (1),nvt (6),Aantal,Eenheid,Tarief,Artikelomschrijving,Factuur nummer,_regelnummer_factuur,data_dir,LogBestand
    -> Sorter_op_factuur-_en_regelnummer
Note: Rapportage: statistiek productgroepen
Junction_3
    -> AttributeManager_5

Bookmark: Prepareer facturatie van contracten apart van de standaard regels
Note: Nieuw factuurnummer maken voor de contractfacturen op basis van ingelezen factuurnummers met toevoeging van een volgnummer per contract. Als er meerdere contracten op een factuur voorkomen dan wordt de factuur gesplitst per contract en iedere contractfactuur krijgt een volgnummer achter de originele factuurnummer
TestFilter
    DEFAULT_VALUE = Contract.Code leeg
    PASSED_TEST_GROUP_OUTPUT = FIRST
    TEST_LIST = "BOOL_OP,OR,COMPOSITE_TEST,""""""1"""""",TEST_CLAUSE,TEST Contract.Code ATTRIBUTE_HAS_A_VALUE """,Contract.Code ATTRIBUTE_HAS_A_VALUE
    Contract.Code ATTRIBUTE_HAS_A_VALUE -> Samenvatten_op_factuurnummer-contractCode
Samenvatten_op_factuurnummer-contractCode: StatisticsCalculator
    ATTR_ACCUM_MODE = None
    CALCULATION_MODE = NUMERIC
    FEAT_STATS = FactuurRegel.Bon.Code,NUMERIC_MODE,,,COUNT,,,,,,,,,,
    GROUP_BY = Contract.Code "Factuur nummer"
    SUMMARY -> Counter_volgnummer_factuur
Note: Als er meerdere contracten zijn per factuur dan krijgen ze per contract.code een volgnummer beginnend met 1
Counter_volgnummer_factuur
    CNT_ATTR = _volgnummer_factuur
    GROUP_BY = "Factuur nummer"
    SCOPE = Local
    START = 1
    -> AttributeCreator__factuurnummer_contract
AttributeCreator__factuurnummer_contract
    ATTR_TABLE = SET_TO _factuurnummer_contract (varchar(200)) = FME_CONDITIONAL:DEFAULT_VALUE'@Value(Factuur nummer)'BOOL_OP;OR;COMPOSITE_TEST;1;TEST Contract.Code ATTRIBUTE_HAS_A_VALUE _FME_BLANK_STRING_'@Value(Factuur nummer)@Value(_volgnummer_factuur)'FME_NUM_CONDITIONS2___
    INPUT_PORT_CONNECTED = CONNECTED
    -> AttributeKeeper_5
AttributeKeeper_5
    CREATE_BULK_MODE_FEATURES = NO
    KEEP_ATTRS = Contract.Code,Factuur nummer,_factuurnummer_contract
    -> Merger_contractfactuurnummers_aan_factuurregels [SUPPLIER]
Merger_contractfactuurnummers_aan_factuurregels: FeatureMerger
    ATTR_ACCUM_MODE = Merge Supplier
    ATTR_CONFLICT_RES_LOOKUP = REQUESTOR_IF_CONFLICT
    IGNORE_NULLS = No
    JOIN_KEYS = @Value(Factuur nummer) @Value(Factuur nummer) AUTO @Value(Contract.Code) @Value(Contract.Code) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeManager_subregels_algemeen
    UNMERGED_REQUESTOR -> AttributeManager_subregels_algemeen

Bookmark: Debiteuren controle + rapportage
Note: FeatureMerger_facturen_bonnen : Merged
Junction_22
    -> DuplicateFilter_Relatie.Code
DuplicateFilter_Relatie.Code
    INPUT_ORDERED_CHOICE_LOOKUP = NO
    KEYATTR = Relatie.Code
    INPUT_ORDERED_CHOICE = No
    UNIQUE -> AttributeKeeper_2
AttributeKeeper_2
    CREATE_BULK_MODE_FEATURES = NO
    KEEP_ATTRS = Relatie.Code,Relatie.Omschrijving
    -> StatisticsCalculator_aantal_debnr_gebruikt
StatisticsCalculator_aantal_debnr_gebruikt
    ATTR_ACCUM_MODE = All
    CALCULATION_MODE = NUMERIC
    FEAT_STATS = Relatie.Code,NUMERIC_MODE,,,COUNT,,,,,,,,,,
    COMPLETE -> FeatureMerger [REQUESTOR]
JSONFragmenter
    EXPLODE_FORMAT = JSON
    EXTRACT_ATTR = Yes
    INPUT_PORT_CONNECTED = CONNECTED
    JSON_ATTR = _response_body
    JSON_QUERY = json["value"][*]
    NEW_ATTRIBUTES = debnr buffer
    READ_FROM_FILE = NO
    RECURSIVE = YES
    REJECT_EMPTY_LISTS = YES
    FRAGMENTS -> TestFilter_debnr_gevuld
TestFilter_debnr_gevuld
    DEFAULT_VALUE = debnr leeg
    PASSED_TEST_GROUP_OUTPUT = FIRST
    TEST_LIST = "BOOL_OP,OR,COMPOSITE_TEST,""""""1"""""",TEST_CLAUSE,TEST debnr ATTRIBUTE_HAS_A_VALUE """,debnr gevuld
    debnr gevuld -> AttributeKeeper_3
AttributeKeeper_3
    CREATE_BULK_MODE_FEATURES = NO
    KEEP_ATTRS = debnr
    -> FeatureMerger [SUPPLIER]
FeatureMerger
    ATTR_ACCUM_MODE = Merge Supplier
    ATTR_CONFLICT_RES_LOOKUP = REQUESTOR_IF_CONFLICT
    IGNORE_NULLS = No
    JOIN_KEYS = @Value(Relatie.Code) @Value(debnr) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> NoFeaturesTester
    UNMERGED_REQUESTOR -> FeatureCounter_aantal
NoFeaturesTester [off]
    NoInput -> AttributeCreator_html_6
    -> StatisticsCalculator_debnr_Checked
StatisticsCalculator_debnr_Checked [off]
    ATTR_ACCUM_MODE = All
    CALCULATION_MODE = NUMERIC
    FEAT_STATS = debnr,NUMERIC_MODE,,,COUNT,,,,,,,,,,
    SUMMARY -> AttributeCreator_html_6
AttributeCreator_html_6 [off]
    ATTR_TABLE:
      SET_TO _debnr_check_result (varchar(200)) = FME_CONDITIONAL:DEFAULT_VALUE'@Evaluate(@Value(Relatie.Code.total_count) - @Value(debnr.total_count))'BOOL_OP;AND;COMPOSITE_TEST;1 AND 2;TEST no_features NOT_ATTRIBUTE_IS_MISSING _FME_BLANK_STRING_;TEST @Value(no_features) = true'0'FME_NUM_CONDITIONS2___
      SET_TO html_content (varchar(200)) = FME_CONDITIONAL:DEFAULT_VALUE'<h4>Debiteurencheck: Alle debiteuren gevonden in IW !</font></h4>
        <table border=1>
           <thead>
              <tr>
                 <th>#Deb in PBA Export</th>
                 <th>#Gevonden in IW</th>
              </tr>
           </thead>
           <tbody>
              <tr>
                 <td>@Value(Relatie.Code.total_count)</td>
                 <td>@Value(debnr.total_count)</td>
              </tr>
           </tbody>
        </table>
        'BOOL_OP;AND;COMPOSITE_TEST;1 AND 2;TEST no_features NOT_ATTRIBUTE_IS_MISSING _FME_BLANK_STRING_;TEST @Value(no_features) = true'<h4><font color=red>Geen debiteurencontrole mogelijk, neem contact op met applicatiebeheerder !</font></h4>'BOOL_OP;OR;COMPOSITE_TEST;1;TEST @Evaluate(@Value(Relatie.Code.total_count)-@Value(debnr.total_count)) > 0'<h4>Debiteurencheck: <font color=red>Niet alle debiteuren gevonden in IW !</font></h4>
        <table border=1>
           <thead>
              <tr>
                 <th>#Deb in PBA Export</th>
                 <th>#Gevonden in Iw</th>
                 <th>#Ontbrekende deb</th>
              </tr>
           </thead>
           <tbody>
              <tr>
                 <td>@Value(Relatie.Code.total_count)</td>
                 <td>@Value(debnr.total_count)</td>
                 <td><font color=red>@Value(_debnr_check_result)</font></td>
              </tr>
           </tbody>
        </table>
        'FME_NUM_CONDITIONS3___
      SET_TO Volgorde (uint8) = 51
    -> Sorter_volgorde
FeatureCounter_aantal
    FeatureCounterNewAttrParameter = _numfeatures
    GroupBox = NO
    -> AttributeCreator_html_8
AttributeCreator_html_8
    ATTR_TABLE:
      SET_TO html_debiteuren (varchar(200)) =       <tr>
                 <td>@Value(Relatie.Code)</td>
                 <td>@Value(Relatie.Omschrijving)</td>
              </tr>
    -> AttributeCombiner_3
AttributeCombiner_3
    ATTRS = html_debiteuren
    DROP_EMPTY = No
    QUOT = None
    -> AttributeCreator_html_9
AttributeCreator_html_9
    ATTR_TABLE:
      SET_TO html_content (varchar(200)) = <h5><font color=red>@Value(_numfeatures) debiteuren niet gevonden in IW </font> Debiteuren (laten) toevoegen in IW voor de import van deze CSV te starten.</h4>
        <table border=1>
           <thead>
              <tr>
                 <th>Debiteurnummer</th>
                 <th>Omschrijving</th>
              </tr>
           </thead>
           <tbody>
        @Value(html_debiteuren)
           </tbody>
        </table>

      SET_TO Volgorde (uint8) = 3
    -> Sorter_volgorde

Bookmark: Rapportage missende bonnen
Note: Als er een factuurregel niet matched op het bonnenbestand betekent dat er bon informatie mist.
Note: FeatureMerger_facturen_bonnen : UnmergedRequestor
Junction_13
    -> AttributeKeeper_missende_bonnen
AttributeKeeper_missende_bonnen
    CREATE_BULK_MODE_FEATURES = NO
    KEEP_ATTRS = Factuur nummer,FactuurRegel.Artikel.Code,FactuurRegel.Artikel.Omschrijving,FactuurRegel.Bon.Code,FactuurRegel.Bon.Datum,FactuurRegel.Hoeveelheid,Factuurrun.Omschrijving,Factuurrun.code,FactuurRegel.Eenheid
    -> AttributeCreator
AttributeCreator
    ATTR_TABLE = SET_TO _artikel_omschrijving (varchar(200)) = @Value(FactuurRegel.Artikel.Code) - @Value(FactuurRegel.Artikel.Omschrijving)
    INPUT_PORT_CONNECTED = CONNECTED
    -> AttributeCreator_html_7
AttributeCreator_html_7
    ATTR_TABLE:
      SET_TO html_artikelen (varchar(200)) =       <tr>
                 <td>@Value(Factuur nummer)</td>
                 <td>@Value(Factuurrun.code)</td>
                 <td>@Value(FactuurRegel.Bon.Code)</td>
                 <td>@Value(FactuurRegel.Bon.Datum)</td>
                 <td>@Value(_artikel_omschrijving)</td>
                 <td>@Value(FactuurRegel.Hoeveelheid)</td>
                 <td>@Value(FactuurRegel.Eenheid)</td>
              </tr>
    -> AttributeCombiner_4
AttributeCombiner_4
    ATTRS = html_artikelen
    DROP_EMPTY = No
    QUOT = None
    -> AttributeCreator_html_10
AttributeCreator_html_10
    ATTR_TABLE:
      SET_TO html_content (varchar(200)) = <h5><font color=red>Ontbrekende bonnen bij facturen.</font> De export van de bonnen is niet compleet. Er zijn factuurregels waarbij de boninformatie niet gevonden kan worden.</h4>
        <table border=1>
           <thead>
              <tr>
                 <th>Factuur</th>
                 <th>Factuurrun</th>
                 <th>Bon</th>
                 <th>Datum</th>
                 <th>Artikel</th>
                 <th>Hvh</th>
                 <th>Eenheid</th>
              </tr>
           </thead>
           <tbody>
        @Value(html_artikelen)
           </tbody>
        </table>

      SET_TO Volgorde (uint8) = 1
    -> Junction_4

Bookmark: Bewerk bondata
Sorter_op_boncode
    SORT_PARM = Code NATURAL ASCENDING
    SORTED -> DuplicateFilter_dubbele_bonregels
DuplicateFilter_dubbele_bonregels
    INPUT_ORDERED_CHOICE_LOOKUP = YES
    KEYATTR = Code
    INPUT_ORDERED_CHOICE = Yes
    UNIQUE -> AttributeManager_veldnamen
AttributeManager_veldnamen
    ATTR_TABLE:
      RENAME_SET_VALUE Werklocatie.Code > Werkorder (varchar(12))
      RENAME_SET_VALUE Geleidebiljet > Begeleidingsbrief (varchar(10))
      REMOVE Werklocatie.Omschrijving (varchar(50))
      REMOVE Gecorrigeerd/tegenboeking (varchar(3))
      REMOVE Correctie weegbon (varchar(8))
    -> FeatureMerger_bondata_aan_factuurregels_koppelen [SUPPLIER]

Bookmark: Data koppelen en bewerken
FeatureMerger_bondata_aan_factuurregels_koppelen
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(Onvangstbonnr) @Value(Code) AUTO
    MERGE_TYPE_VAL = ATTRIBUTES
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGE_TYPE = Attributes Only
    MERGED -> AttributeManager
    MERGED -> Junction_6
Note: StatisticsCalculator_2 : Input
Junction_6
    -> Junction_18
AttributeManager
    ATTR_TABLE:
      SET_TO BTW (number(2,0)) = @Trim(@Value(BTW))
      REMOVE Code (varchar(8))
    -> StringReplacer_punt_komma_getallen
StringReplacer_punt_komma_getallen
    CASE = NO
    FIND_TEXT = .
    NO_MATCH = _FME_NO_OP_
    REGEXP = NO
    REPLACE_TEXT = ,
    SRC_ATTRS = Aantal,Prijs
    -> AttributeCreator_CSVBestand_2
AttributeCreator_CSVBestand_2
    ATTR_TABLE = SET_TO CSVBestand (varchar(200)) = BV_@Value(Relatie.Code)_Ontvangsten_$(_zone_timestamp)
    INPUT_PORT_CONNECTED = CONNECTED
    -> FeatureWriter_CSV [Output]

Bookmark: Schrijf CSV en mail resultaten
FeatureWriter_CSV
    CONFIG_PARAMETERS = ESCAPE_COMMAS_IN_FTP_FORMAT_PARAMETERS,no
    CSV2_COORDINATE_DETECTION_MODE = automatic
    CSV2_COORDINATE_SYSTEM_GRANULARITY = FEATURE_TYPE
    CSV2_DELIMITER = ;
    CSV2_ENCODING = UTF-8
    CSV2_EXISTING_FILE_HANDLING = Yes
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = @Value(destination_dir)
    DATASET_ATTR = _dataset
    FEATURE_TYPE_LIST_ATTR = _feature_types
    FORMAT = CSV2
    MORE_SUMMARY_ATTRS = destination_dir
    TOTAL_FEATURES_WRITTEN_ATTR = _total_features_written
    SUMMARY -> ListExploder_2
ListExploder_2
    ATTR_CONFLICT_RES_LOOKUP = INCOMING_IF_CONFLICT
    INDEX_ATTR = _element_index
    LIST_ATTR = _feature_types{}
    ATTR_ACCUM_MODE = Merge List Attributes
    ATTR_CONFLICT_RES = Use List Attribute Values
    ELEMENTS -> FeatureMerger_5 [REQUESTOR]
FeatureMerger_5
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeCreator_System_Bijlage_2
AttributeCreator_System_Bijlage_2
    ATTR_TABLE = SET_TO Bijlage (varchar(200)) = FME_CONDITIONAL:DEFAULT_VALUE'@Value(destination_dir)/@Value(name).csv'BOOL_OP;OR;COMPOSITE_TEST;1;TEST $(FME_OS) = Wndows'@Value(destination_dir)\@Value(name).csv'FME_NUM_CONDITIONS2___
    -> StringReplacer_newlines_2
StringReplacer_newlines_2
    CASE = NO
    NO_MATCH = _FME_NO_OP_
    REGEXP = NO
    STR_REPLACE_TABLE = "html_content \n "
    -> TestFilter_FME_OS_2
    -> Sampler_2
TestFilter_FME_OS_2
    DEFAULT_VALUE = FME Flow
    PASSED_TEST_GROUP_OUTPUT = FIRST
    TEST_LIST = "BOOL_OP,OR,COMPOSITE_TEST,""""""1"""""",TEST_CLAUSE,TEST $(FME_OS) = Windows",Windows = local
    Windows = local -> GKB_EmailGenerator_local_zonder_bijlage_2
    FME Flow -> GKB_EmailGenerator_2
GKB_EmailGenerator_local_zonder_bijlage_2
    Body = @Value(html_content)
    Subject = $(_zone_timestamp)
    To = $(ResultaatEmail)
    VERZAMEL_MAIL = YES
GKB_EmailGenerator_2
    ATTACHMENT = @Value(Bijlage)
    Body = @Value(html_content)
    CC = dirkjan@gkbgroep.nl
    Subject = PBA-IW ontvangsten $(_zone_timestamp)
    To = $(ResultaatEmail)
    VERZAMEL_MAIL = YES

Bookmark: SCHRIJF HTML Log naar run folder
Sampler_2
    MODE = ORIGINAL
    RATE = 1
    SAMPLE_TYPE_MULTIPLIER = -1
    SAMPLE_MODE = No
    SAMPLE_TYPE_LONG = First N Features
    SAMPLED -> AttributeCreator_filecopy_source_dataset_4
AttributeCreator_filecopy_source_dataset_4
    ATTR_TABLE = SET_TO filecopy_source_dataset (varchar(200)) = @Value(destination_dir)\log_ontvangsten_$(_zone_timestamp).html
    INPUT_PORT_CONNECTED = CONNECTED
    -> FeatureWriter_html_log_2 [HTML]
FeatureWriter_html_log_2
    CONFIG_PARAMETERS = ESCAPE_COMMAS_IN_FTP_FORMAT_PARAMETERS,no
    DATASET = @Value(filecopy_source_dataset)
    DATASET_ATTR = _dataset
    FEATURE_TYPE_LIST_ATTR = _feature_types
    FORMAT = HTML
    HTML_COORDINATE_SYSTEM_GRANULARITY = FEATURE
    HTML_DESTINATION_DATASETTYPE_VALIDATION = Yes
    HTML_ENCODING = UTF8
    HTML_END_OF_LINE = System
    HTML_MIME_TYPE = text/html
    HTML_OVERWRITE_FILE = YES
    HTML_WRITE_LAST_EOL = YES
    HTML_WRITE_UTF8_BOM = YES
    MORE_SUMMARY_ATTRS = destination_dir
    TOTAL_FEATURES_WRITTEN_ATTR = _total_features_written
    SUMMARY -> FeatureWriter_COPY_HTML_LOG_2 [Summary]
FeatureWriter_COPY_HTML_LOG_2
    CONFIG_PARAMETERS = ESCAPE_COMMAS_IN_FTP_FORMAT_PARAMETERS,no
    DATASET = @Value(_feature_types{0}.destination_dir)
    DATASET_ATTR = _dataset
    FEATURE_TYPE_LIST_ATTR = _feature_types
    FILECOPY_COORDINATE_SYSTEM_GRANULARITY = FEATURE
    FILECOPY_COPY_SOURCE_DIRECTORY = NO
    FILECOPY_COPY_SUBDIRECTORIES = NO
    FILECOPY_DESTINATION_DATASETTYPE_VALIDATION = Yes
    FILECOPY_FAIL_INVALID_DESTINATION = NO
    FILECOPY_FAIL_NONEXISTENT_SOURCE = NO
    FILECOPY_FEATURE_TYPE_NAMES_AS_FOLDERS = NO
    FILECOPY_FILE_OPERATION = COPY
    FILECOPY_MIME_TYPE = application/vnd.openxmlformats-officedocument.spreadsheetml.sheet
    FILECOPY_OVERWRITE_FILE = YES
    FORMAT = FILECOPY
    TOTAL_FEATURES_WRITTEN_ATTR = _total_features_written

Bookmark: destination_dir toevoegen aan
Sampler
    MODE = ORIGINAL
    RATE = 1
    SAMPLE_TYPE_MULTIPLIER = -1
    SAMPLE_MODE = No
    SAMPLE_TYPE_LONG = First N Features
    SAMPLED -> AttributeKeeper_11
AttributeKeeper_11
    CREATE_BULK_MODE_FEATURES = NO
    KEEP_ATTRS = destination_dir
    -> FeatureMerger_destination_dir [SUPPLIER]
FeatureMerger_destination_dir
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> StringReplacer_newlines

Bookmark: Ophalen artikelen met API (data-virtualisatie) FME
HTTPCaller
    CLIENT_CERTIFICATE_TYPE = NONE
    CONNECTION_TIMEOUT_LENGTH = 60
    CUSTOM_HEADERS = Authorization;fmetoken token=@Value(_token_indexatie_API)
    ERROR_ATTR = _error
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = @Value(_url_get_artikelen)
    TRANSFER_TIMEOUT_LENGTH = 90
    USE_COOKIES = No
    VERIFY_SSL_CERTIFICATES = Yes
    -> JSONFragmenter_2
    <REJECTED> -> AttributeCreator_log_message
JSONFragmenter_2
    EXPLODE_FORMAT = JSON
    EXTRACT_ATTR = Yes
    INPUT_PORT_CONNECTED = CONNECTED
    JSON_ATTR = _response_body
    JSON_QUERY = json[*]
    NEW_ATTRIBUTES = Artikel.Code buffer Artikel.Omschrijving buffer Productgroep buffer
    READ_FROM_FILE = NO
    RECURSIVE = YES
    REJECT_EMPTY_LISTS = YES
    FRAGMENTS -> FeatureMerger_productgroep [SUPPLIER]
AttributeCreator_log_message
    ATTR_TABLE:
      SET_TO _log_message (varchar(200)) = <font color=red>Foutmelding</font> HTTPCaller Artikelen: @Value(_http_status_code) : @Value(_response_body)
      SET_TO _log_volgorde (uint8) = 1
    INPUT_PORT_CONNECTED = CONNECTED
    -> AttributeKeeper_9

Bookmark: MAAK Indexatieregels
FeatureMerger_productgroep
    ATTR_ACCUM_MODE = Merge Supplier
    ATTR_CONFLICT_RES_LOOKUP = REQUESTOR_IF_CONFLICT
    IGNORE_NULLS = No
    JOIN_KEYS = @Value(FactuurRegel.Artikel.Code) @Value(Artikel.Code) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> FeatureMerger_indexatie [REQUESTOR]
    UNMERGED_REQUESTOR -> Junction_14
Note: Rapporteer artikelen die niet gevonden zijn in de ariktel lijst
Junction_14
    -> Junction_15
FeatureMerger_indexatie
    ATTR_ACCUM_MODE = Merge Supplier
    ATTR_CONFLICT_RES_LOOKUP = REQUESTOR_IF_CONFLICT
    IGNORE_NULLS = No
    JOIN_KEYS = @Value(Productgroep) @Value(Naam) AUTO @Value(_bon_week) @Value(Week) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeCreator_indexatie
    UNMERGED_REQUESTOR -> Sorter_F_-_A_-_T
AttributeCreator_indexatie
    ATTR_TABLE:
      SET_TO BTWTarief (real32) = 0.21
      SET_TO IndexatieTarief (real64) = @Evaluate((@Value(Indexatie)/100)*@Value(FactuurRegel.Tarief))
      SET_TO IndexatieBedragExBTW (real64) = @Evaluate(@Value(IndexatieTarief)*@Value(Aantal))
      SET_TO IndexatieBedragBTW (real64) = @Evaluate(@Value(BTWTarief)*@Value(IndexatieBedragExBTW))
    INPUT_PORT_CONNECTED = CONNECTED
    -> Sorter_F_-_A_-_T
    -> Junction_29
Junction_29
    -> AttributeRounder_6
AttributeRounder_6
    PLACES = 2
    ROUND_TYPE_TCL = round
    SRC_ATTRS = BTW bedrag regel Bedrag IndexatieBedragBTW IndexatieBedragExBTW IndexatieTarief
    ROUND_TYPE = Nearest
    -> Junction_30
Tel_regels_per_factuurnummer_als_regelnummer: Counter
    CNT_ATTR = _regelnummer_factuur
    GROUP_BY = "Factuur nummer"
    SCOPE = Local
    START = 1
    -> Counter_factuur_artikel_week_regels_2
Counter_factuur_artikel_week_regels_2
    CNT_ATTR = _regelnummer_factuur_artikel_week
    GROUP_BY = "Factuur nummer" FactuurRegel.Artikel.Code FactuurRegel.Tarief _bon_week
    SCOPE = Local
    START = 101
    -> FeatureCounter_factuur-artikel
Note: EXCEL_LOG_WRITER : STAT_INDEXATIE
FeatureCounter_factuur-artikel
    FeatureCounterNewAttrParameter = _max_regelnummer_factuur_artikel_bon_week
    GROUP_BY = "Factuur nummer" FactuurRegel.Artikel.Code FactuurRegel.Tarief _bon_week
    GroupBox = YES
    -> TestFilter_artikel_regelnummer
    -> AttributeManager_ARTIKEL_regel
    -> FeatureMerger_2 [REQUESTOR]
Note: Rapportage:_INDEXATIE
Junction_2
    -> Junction_11

Bookmark: Rapportage missende bonnen
Note: Rapporteer artikelen die niet gevonden zijn in de ariktel lijst
Junction_15
    -> AttributeKeeper_missende_bonnen_2
AttributeKeeper_missende_bonnen_2
    CREATE_BULK_MODE_FEATURES = NO
    KEEP_ATTRS = FactuurRegel.Artikel.Code,FactuurRegel.Artikel.Omschrijving,FactuurRegel.Bon.Code,FactuurRegel.Hoeveelheid,FactuurRegel.Eenheid
    -> StatisticsCalculator
StatisticsCalculator
    ATTR_ACCUM_MODE = One
    CALCULATION_MODE = NUMERIC
    FEAT_STATS = FactuurRegel.Hoeveelheid,NUMERIC_MODE,,,,SUM,,,,,,,,,;FactuurRegel.Bon.Code,NUMERIC_MODE,,,COUNT,,,,,,,,,,
    GROUP_BY = FactuurRegel.Artikel.Code
    SUMMARY -> AttributeCreator_html_11
AttributeCreator_html_11
    ATTR_TABLE:
      SET_TO html_artikelen (varchar(200)) =       <tr>
                 <td>@Value(FactuurRegel.Bon.Code.total_count)</td>
                 <td>@Value(FactuurRegel.Artikel.Code)</td>
                 <td>@Value(FactuurRegel.Artikel.Omschrijving)</td>
                 <td>@Value(FactuurRegel.Eenheid)</td>
                 <td>@Value(FactuurRegel.Hoeveelheid.sum)</td>
              </tr>
    -> AttributeCombiner_5
AttributeCombiner_5
    ATTRS = html_artikelen
    DROP_EMPTY = No
    QUOT = None
    -> AttributeCreator_html_12
AttributeCreator_html_12
    ATTR_TABLE:
      SET_TO html_content (varchar(200)) = <h5><font color=red>Artikelen niet gevonden in artikellijst.</font> Hiermee kan geen indexatie van deze artikelen vastgesteld worden.</h4>
        <table border=1>
           <thead>
              <tr>
                 <td>#Bonnen</td>
                 <td>Artikel</td>
                 <td>Omschrijving</td>
                 <td>Eenheid</td>
                 <td>Aantal</td>
              </tr>
           </thead>
           <tbody>
        @Value(html_artikelen)
           </tbody>
        </table>

      SET_TO Volgorde (uint8) = 2
    -> Junction_4

Bookmark: Ophalen indexaties - productgroepen met API (data-virtualisatie) FME
HTTPCaller_2
    CLIENT_CERTIFICATE_TYPE = NONE
    CONNECTION_TIMEOUT_LENGTH = 60
    CUSTOM_HEADERS = Authorization;fmetoken token=@Value(_token_indexatie_API)
    ERROR_ATTR = _error
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = @Value(_url_get_indexaties)
    TRANSFER_TIMEOUT_LENGTH = 90
    USE_COOKIES = No
    VERIFY_SSL_CERTIFICATES = Yes
    -> JSONFragmenter_3
    <REJECTED> -> AttributeCreator_log_message_2
JSONFragmenter_3
    EXPLODE_FORMAT = JSON
    EXTRACT_ATTR = Yes
    INPUT_PORT_CONNECTED = CONNECTED
    JSON_ATTR = _response_body
    JSON_QUERY = json[*]
    NEW_ATTRIBUTES = Naam buffer Jaar int32 Week int32 Indexatie number(20,10)
    READ_FROM_FILE = NO
    RECURSIVE = YES
    REJECT_EMPTY_LISTS = YES
    FRAGMENTS -> FeatureMerger_indexatie [SUPPLIER]
    FRAGMENTS -> AttributeKeeper_6
AttributeCreator_log_message_2
    ATTR_TABLE:
      SET_TO _log_message (varchar(200)) = <font color=red>Foutmelding</font> HTTPCaller Productgroepen: @Value(_http_status_code) : @Value(_response_body)
      SET_TO _log_volgorde (uint8) = 11
    INPUT_PORT_CONNECTED = CONNECTED
    -> AttributeKeeper_9

Bookmark: (no name)
Sorter_F_-_A_-_T
    SORT_PARM = Factuur nummer NATURAL ASCENDING NON_VALUES_AFTER_VALUES FactuurRegel.Artikel.Code NATURAL ASCENDING NON_VALUES_AFTER_VALUES FactuurRegel.Tarief NATURAL ASCENDING NON_VALUES_AFTER_VALUES _bon_week NATURAL ASCENDING NON_VALUES_AFTER_VALUES
    SORTED -> Tel_regels_per_factuurnummer_als_regelnummer

Bookmark: (no name)
AttributeManager_ARTIKEL_regel
    ATTR_TABLE:
      SET_TO _artikel_regel (uint8) = 1
      SET_TO _index_regel (uint8) = 0
      SET_TO _rgsoort (varchar(5)) = BASIS
      RENAME_SET_VALUE Artikel.Code > ArtikelCode (varchar(7))
      SET_TO Bedrag (real64) = @Evaluate(@Value(FactuurRegel.Bedrag excl. Btw))
      REMOVE IndexatieTarief (real64)
      SET_TO BTW bedrag regel (real32) = @Value(FactuurRegel.Bedrag Btw)
      SET_TO Factuuregelomschrijving (varchar(200)) = @TrimRight(@Value(Artikel.Omschrijving)#@Value(Datum)#@Value(Kenteken)#@Value(Referentie), #)
      SET_TO Week (int32) = FME_CONDITIONAL:DEFAULT_VALUE'_FME_NO_OP_'BOOL_OP;OR;COMPOSITE_TEST;1;TEST Week ATTRIBUTE_IS_MISSING _FME_BLANK_STRING_'@Value(_bon_week)'FME_NUM_CONDITIONS2___
      REMOVE BTWTarief (real32)
      REMOVE IndexatieBedragExBTW (real64)
      REMOVE IndexatieBedragBTW (real64)
      SET_TO _aantal_bonregels (uint8) = 1
    USER_EXPOSED_ATTRIBUTES = IndexatieBedrag
    -> Junction_3
    -> AttributeRounder_4

Bookmark: Positie indexregel binnen factuurregels bepalen
TestFilter_artikel_regelnummer
    DEFAULT_VALUE = kleiner dan
    PASSED_TEST_GROUP_OUTPUT = FIRST
    TEST_LIST = "BOOL_OP,OR,COMPOSITE_TEST,""""""1"""""",TEST_CLAUSE,TEST @Value(_regelnummer_factuur_artikel_week) = @Evaluate(100 + @Value(_max_regelnummer_factuur_artikel_bon_week))",maxvalue
    maxvalue -> AttributeCreator__regelnummer_factuur_indexregel
AttributeCreator__regelnummer_factuur_indexregel
    ATTR_TABLE = SET_TO _regelnummer_factuur_indexregel (real64) = @Evaluate(@Value(_regelnummer_factuur)+0.5)
    INPUT_PORT_CONNECTED = CONNECTED
    -> AttributeKeeper_4
AttributeKeeper_4
    CREATE_BULK_MODE_FEATURES = NO
    KEEP_ATTRS = Factuur nummer,FactuurRegel.Artikel.Code,FactuurRegel.Tarief,_regelnummer_factuur_indexregel,LogBestand,_bon_week
    -> FeatureMerger_2 [SUPPLIER]
FeatureMerger_2
    ATTR_ACCUM_MODE = Merge Supplier
    ATTR_CONFLICT_RES_LOOKUP = REQUESTOR_IF_CONFLICT
    IGNORE_NULLS = No
    JOIN_KEYS = @Value(Factuur nummer) @Value(Factuur nummer) AUTO @Value(FactuurRegel.Artikel.Code) @Value(FactuurRegel.Artikel.Code) AUTO @Value(FactuurRegel.Tarief) @Value(FactuurRegel.Tarief) AUTO @Value(_bon_week) @Value(_bon_week) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> TestFilter_Indexatie___0

Bookmark: (no name)
TestFilter_Indexatie___0
    DEFAULT_VALUE = Indexatie = 0 of voor 16-03-2026
    PASSED_TEST_GROUP_OUTPUT = FIRST
    TEST_LIST:
      "BOOL_OP,AND,COMPOSITE_TEST,""""""1 AND 2"""""",TEST_CLAUSE,TEST @Value(Indexatie) > 0
      TEST @Value(_interval_week) >= 0",Indexatie en interval_week groter dan 0
    Indexatie en interval_week groter dan 0 -> StatisticsCalculator_2

Bookmark: Groeperen per factuur-artikelcode-tarief_week
StatisticsCalculator_2
    ATTR_ACCUM_MODE = One
    CALCULATION_MODE = NUMERIC
    FEAT_STATS = FactuurRegel.Hoeveelheid,NUMERIC_MODE,,,,SUM,,,,,,,,,;Factuur nummer,NUMERIC_MODE,,,COUNT,,,,,,,,,,;IndexatieBedragBTW,NUMERIC_MODE,,,,SUM,,,,,,,,,;IndexatieBedragExBTW,NUMERIC_MODE,,,,SUM,,,,,,,,,;Aantal,NUMERIC_MODE,,,,SUM,,,,,,,,,
    GROUP_BY = "Factuur nummer" FactuurRegel.Artikel.Code FactuurRegel.Tarief _bon_week
    SUMMARY -> AttributeManager_INDEX_regel
    SUMMARY -> Junction_25
Junction_25
    -> Junction_26

Bookmark: (no name)
AttributeManager_INDEX_regel
    ATTR_TABLE:
      SET_TO _index_regel (uint8) = 1
      SET_TO _artikel_regel (uint8) = 0
      SET_TO _rgsoort (varchar(5)) = INDEX
      RENAME_SET_VALUE Artikel.Code > ArtikelCode (varchar(7))
      SET_TO Artikelomschrijving (varchar(3)) = Toeslag w@Value(_bon_week) (@Value(Indexatie)%) @Value(FactuurRegel.Hoeveelheid.sum) @Value(FactuurRegel.Eenheid)
      REMOVE Artikel.Omschrijving (varchar(47))
      SET_TO Bedrag (real32) = @Value(IndexatieBedragExBTW.sum)
      SET_TO Tarief (real32) = @Value(IndexatieTarief)
      SET_TO FactuurRegel.Bedrag excl. Btw (number(7,2))
      SET_TO FactuurRegel.Bedrag Btw (number(6,2))
      SET_TO BTW bedrag regel (real32) = @Value(IndexatieBedragBTW.sum)
      SET_TO Grootboekrekening (varchar(14)) = 80121
      SET_TO Regelnummer (uint32)
      SET_TO Aantal (real32) = @Value(FactuurRegel.Hoeveelheid.sum)
      SET_TO IndexatieBedragExBTW (real64) = @Value(IndexatieBedragExBTW.sum)
      SET_TO IndexatieBedragBTW (real64) = @Value(IndexatieBedragBTW.sum)
      SET_TO _aantal_bonregels (uint8) = 0
      SET_TO _regelnummer_factuur (int64) = @Value(_regelnummer_factuur_indexregel)
      RENAME_SET_VALUE Aantal.sum > Aantal (real64)
    -> AttributeRounder_4
    -> Junction_3
    -> Junction_2

Bookmark: Hoofdregels maken
Note: Sorter_2 :subregels
Junction_8
    -> StatisticsCalculator_bedragen_en_regels_per_factuur_2
StatisticsCalculator_bedragen_en_regels_per_factuur_2
    ATTR_ACCUM_MODE = One
    CALCULATION_MODE = NUMERIC
    FEAT_STATS = Bedrag,NUMERIC_MODE,,,,SUM,,,,,,,,,;BTW bedrag regel,NUMERIC_MODE,,,,SUM,,,,,,,,,;Factuur nummer,NUMERIC_MODE,,,COUNT,,,,,,,,,,;_artikel_regel,NUMERIC_MODE,,,,SUM,,,,,,,,,;_index_regel,NUMERIC_MODE,,,,SUM,,,,,,,,,;_aantal_bonregels,NUMERIC_MODE,,,,SUM,,,,,,,,,
    GROUP_BY = "Factuur nummer"
    SUMMARY -> DuplicateFilter_Factuur_nummer
    SUMMARY -> Junction_9
DuplicateFilter_Factuur_nummer
    INPUT_ORDERED_CHOICE_LOOKUP = NO
    KEYATTR = Factuurnummer
    INPUT_ORDERED_CHOICE = No
    UNIQUE -> StringSearcher__blokhaken__in_toevoeging
Note: Afspraak format in export voor alternatieve debiteurnummers in specifiek veld met blokhaken als markering
StringSearcher__blokhaken__in_toevoeging
    CASE = no
    MATCHED_PARTS_ATTR = _vervangende_debiteur
    MATCHED_RESULT_ATTR = _first_match
    REGEXP = \[(\d.*)\]
    STRING_TO_SEARCH = @Value(Relatie.Adres.Toevoeging)
    MATCHED -> AttributeManager_7
    NOT_MATCHED -> AttributeManager_7
AttributeManager_hoofdregels
    ATTR_TABLE:
      SET_TO Relatie.Code (int16) = FME_CONDITIONAL:DEFAULT_VALUE'@Value(_vervangende_debiteur{0}.part)'BOOL_OP;OR;COMPOSITE_TEST;1;TEST _vervangende_debiteur{0}.part ATTRIBUTE_IS_MISSING _FME_BLANK_STRING_'@Value(Relatie.Code)'FME_NUM_CONDITIONS2___
      SET_TO Bedrag (real64) = @Evaluate(@Value(Bedrag.sum) + @Value(BTW bedrag regel.sum))
      SET_TO BTW bedrag regel (real32) = 0
      SET_TO BTWsoort (varchar(14)) = FME_NULL_VALUE
      SET_TO Dagboekcode (varchar(14)) = FME_NULL_VALUE
      SET_TO Dagboeknummer (varchar(14)) = FME_NULL_VALUE
      SET_TO Debiteurnummer (uint32) = @Value(Relatie.Code)
      SET_TO Factuurdatum (date) = @DateTimeFormat(@Value(Factuur datum),%d%m%Y)
      SET_TO Factuuregelomschrijving (varchar(200)) = @Value(_factuur_info)
      SET_TO Factuurnummer (varchar(50)) = @Value(Factuur nummer)
      SET_TO Grootboekrekening (varchar(14)) = FME_NULL_VALUE
      SET_TO nvt (1) (varchar(14)) = @Value(Factuurrun.code)
      SET_TO nvt (6) (varchar(14)) = FME_NULL_VALUE
      SET_TO Periode (varchar(14)) = @Format(%2d, @DateTimeFormat(@Value(Factuur datum),%m))
      SET_TO Referentie (varchar(14)) = FME_NULL_VALUE
      SET_TO Regelnummer (uint32) = 0
      SET_TO Valuta (varchar(3)) = EUR
      SET_TO Vervaldatum factuur (varchar(14)) = @DateTimeFormat(@Value(Vervaldatum),%d%m%Y)
      SET_TO Vervaldatum KB (varchar(14)) = FME_NULL_VALUE
      SET_TO _regelnummer_factuur (int64) = 0
    -> AttributeKeeper_hoofdregel
AttributeKeeper_hoofdregel
    CREATE_BULK_MODE_FEATURES = NO
    KEEP_ATTRS = BTW bedrag regel,BTWsoort,Bedrag,Dagboekcode,Dagboeknummer,Debiteurnummer,Factuurdatum,Factuuregelomschrijving,Factuurnummer,Grootboekrekening,Periode,Referentie,Regelnummer,Valuta,Vervaldatum KB,Vervaldatum factuur,nvt (1),nvt (6),Factuur nummer.total_count,Factuur nummer,_regelnummer_factuur,data_dir,Relatie.Omschrijving,LogBestand
    -> Sorter_op_factuur-_en_regelnummer
Note: StatisticsCalculator_TOTAAL : Input
Junction_9
    -> Junction_10

Bookmark: Maak factuurinfo
AttributeManager_7
    ATTR_TABLE:
      SET_TO _referentie (varchar(200)) = FME_CONDITIONAL:DEFAULT_VALUE'_FME_NO_OP_'BOOL_OP;OR;COMPOSITE_TEST;1;TEST Referentie ATTRIBUTE_HAS_A_VALUE _FME_BLANK_STRING_'#Ref: @Value(Referentie)'FME_NUM_CONDITIONS2___
      SET_TO _werklocatie_code (varchar(200)) = FME_CONDITIONAL:DEFAULT_VALUE'_FME_NO_OP_'BOOL_OP;OR;COMPOSITE_TEST;1 OR 2;TEST Werklocatie.Omschrijving ATTRIBUTE_HAS_A_VALUE _FME_BLANK_STRING_;TEST Werklocatie.Code ATTRIBUTE_HAS_A_VALUE _FME_BLANK_STRING_'@Trim(#Locatie: @Value(Werklocatie.Code) @Value(Werklocatie.Omschrijving))'FME_NUM_CONDITIONS2___
      SET_TO _contract_code (varchar(200)) = FME_CONDITIONAL:DEFAULT_VALUE'_FME_NO_OP_'BOOL_OP;OR;COMPOSITE_TEST;1 OR 2;TEST Contract.Code ATTRIBUTE_HAS_A_VALUE _FME_BLANK_STRING_;TEST Contract.Omschrijving ATTRIBUTE_HAS_A_VALUE _FME_BLANK_STRING_'@Trim(#Contract: @Value(Contract.Code) @Value(Contract.Omschrijving))'FME_NUM_CONDITIONS2___
    -> AttributeCreator_factuur_info
AttributeCreator_factuur_info
    ATTR_TABLE = SET_TO _factuur_info (varchar(200)) = FME_CONDITIONAL:DEFAULT_VALUE'Gefactureerd: @Value(_aantal_bonregels.sum) bon(nen).@Value(_referentie)@Value(_werklocatie_code)'BOOL_OP;OR;COMPOSITE_TEST;1;TEST _contract_code ATTRIBUTE_HAS_A_VALUE _FME_BLANK_STRING_'Gefactureerd: @Value(_aantal_bonregels.sum) bon(nen).@Value(_contract_code)@Value(_werklocatie_code)'FME_NUM_CONDITIONS2___
    INPUT_PORT_CONNECTED = CONNECTED
    -> AttributeTrimmer
AttributeTrimmer
    SRC_ATTRS = _factuur_info
    TRIM_CHARS = "# "
    TRIM_TO_NONE = Yes
    TRIM_TYPE = BOTH
    -> StringReplacer_14
StringReplacer_14
    CASE = NO
    NO_MATCH = _FME_NO_OP_
    REGEXP = NO
    STR_REPLACE_TABLE = _factuur_info ## #
    -> AttributeManager_hoofdregels

Bookmark: TOTALEN
Note: StatisticsCalculator_bedragen_en_regels_per_factuur_2 : Summary
Junction_10
    -> StatisticsCalculator_TOTAAL_2
StatisticsCalculator_TOTAAL_2
    ATTR_ACCUM_MODE = None
    CALCULATION_MODE = NUMERIC
    FEAT_STATS = Bedrag.sum,NUMERIC_MODE,,,,SUM,,,,,,,,,;BTW bedrag regel.sum,NUMERIC_MODE,,,,SUM,,,,,,,,,;Factuur nummer.total_count,NUMERIC_MODE,,,COUNT,SUM,,,,,,,,,
    SUMMARY -> AttributeRounder_3
AttributeRounder_3
    PLACES = 2
    ROUND_TYPE_TCL = round
    SRC_ATTRS = BTW bedrag regel.sum.sum Bedrag.sum.sum
    ROUND_TYPE = Nearest
    -> NumberSeparator
NumberSeparator
    NumberSeparatorPrefix = €
    NumberSeparatorSeparatorChar = comma
    ToBeCreated = TotaalBedragExcl
    _AREA = @Value(Bedrag.sum.sum)
    -> NumberSeparator_2
NumberSeparator_2
    NumberSeparatorPrefix = €
    NumberSeparatorSeparatorChar = comma
    ToBeCreated = TotaalBedragBTW
    _AREA = @Value(BTW bedrag regel.sum.sum)
    -> StringReplacer
StringReplacer
    CASE = NO
    FIND_TEXT = .
    NO_MATCH = _FME_NO_OP_
    REGEXP = NO
    REPLACE_TEXT = #
    SRC_ATTRS = TotaalBedragBTW,TotaalBedragExcl
    -> StringReplacer_2
StringReplacer_2
    CASE = NO
    FIND_TEXT = ,
    NO_MATCH = _FME_NO_OP_
    REGEXP = NO
    REPLACE_TEXT = .
    SRC_ATTRS = TotaalBedragBTW,TotaalBedragExcl
    -> StringReplacer_3
StringReplacer_3
    CASE = NO
    FIND_TEXT = #
    NO_MATCH = _FME_NO_OP_
    REGEXP = NO
    REPLACE_TEXT = ,
    SRC_ATTRS = TotaalBedragBTW,TotaalBedragExcl
    -> AttributeCreator_html
AttributeCreator_html
    ATTR_TABLE:
      SET_TO html_content (varchar(200)) = <h4>Totaal bedragen (incl. indexatie)</h4>
              <table border=1>
                 <thead>
                    <tr>
                       <th>Facturen</th>
                       <th>Factuurregels</th>
                       <th>Totaal bedrag (excl.)</th>
                       <th>Totaal BTW</th>
                    </tr>
                 </thead>
                 <tbody>
                    <tr>
                        <td>@Value(Factuur nummer.total_count.total_count)</td>
                        <td>@Value(Factuur nummer.total_count.sum)</td>
                        <td>@Value(TotaalBedragExcl)</td>
                        <td>@Value(TotaalBedragBTW)</td>
                    </tr>
                 </tbody>
              </table>

      SET_TO Volgorde (uint8) = 11
    -> Sorter_volgorde

Bookmark: OUTPUT CSV Schrijven en mailen
Sorter_op_factuur-_en_regelnummer
    SORT_PARM = Factuurnummer ALPHA ASCENDING _regelnummer_factuur NATURAL ASCENDING
    SORTED -> Counter_Regelnummer
Counter_Regelnummer
    CNT_ATTR = Regelnummer
    GROUP_BY = "Factuur nummer"
    SCOPE = Local
    START = 100
    -> AttributeManager_6
AttributeManager_6
    ATTR_TABLE = SET_TO Regelnummer (uint32) = FME_CONDITIONAL:DEFAULT_VALUE'_FME_NO_OP_'BOOL_OP;OR;COMPOSITE_TEST;1;TEST @Value(Regelnummer) = 100'0'FME_NUM_CONDITIONS2___
    -> FeatureMerger_FMUTA6_Schema [REQUESTOR]
AttributeKeeper
    CREATE_BULK_MODE_FEATURES = NO
    KEEP_LIST = attribute{}.fme_data_type attribute{}.name attribute{}.native_data_type attribute{}
    -> FeatureMerger_FMUTA6_Schema [SUPPLIER]
FeatureMerger_FMUTA6_Schema
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> StringFormatter_bedragen
StringFormatter_bedragen
    FORMAT = .2f
    SRC_ATTRS = "BTW bedrag regel",Bedrag,Aantal,Tarief
    -> StringReplacer_punt_naar_komma
StringReplacer_punt_naar_komma
    CASE = NO
    FIND_TEXT = .
    NO_MATCH = _FME_NO_OP_
    REGEXP = NO
    REPLACE_TEXT = ,
    SRC_ATTRS = Bedrag,BTW bedrag regel,Aantal,Tarief
    -> AttributeCreator_CSVBestand
AttributeCreator_CSVBestand
    ATTR_TABLE:
      SET_TO CSVBestand (varchar(200)) = PB_Factuur_FMUTA6_$(_zone_timestamp)
      SET_TO destination_dir (varchar(200)) = FME_CONDITIONAL:DEFAULT_VALUE'@Value(data_dir)/Factuurrun_@Value(CSVBestand)'BOOL_OP;OR;COMPOSITE_TEST;1;TEST $(FME_OS) = Windows'@Value(data_dir)\Factuurrun_@Value(CSVBestand)'FME_NUM_CONDITIONS2___
    INPUT_PORT_CONNECTED = CONNECTED
    -> FeatureWriter [Merged]
    -> Junction_23
FeatureWriter
    CONFIG_PARAMETERS = ESCAPE_COMMAS_IN_FTP_FORMAT_PARAMETERS,no
    CSV2_COORDINATE_DETECTION_MODE = automatic
    CSV2_COORDINATE_SYSTEM_GRANULARITY = FEATURE_TYPE
    CSV2_DELIMITER = ;
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = no
    CSV2_QUALIFY_FIELD_VALUES = yes
    CSV2_ROW_TERMINATION = System
    CSV2_TREAT_EMBEDDED_FIELD_QUALIFIERS_AS_UNSAFE = Yes
    CSV2_WRITE_BOM_FOR_UNICODE = No
    CSV2_WRITE_FIELD_NAMES = no
    CSV2_WRITE_SCHEMA_FILE = NO
    DATASET = @Value(destination_dir)
    DATASET_ATTR = _dataset
    FEATURE_TYPE_LIST_ATTR = _feature_types
    FORMAT = CSV2
    MORE_SUMMARY_ATTRS = destination_dir
    TOTAL_FEATURES_WRITTEN_ATTR = _total_features_written
    SUMMARY -> ListExploder
ListExploder
    ATTR_CONFLICT_RES_LOOKUP = INCOMING_IF_CONFLICT
    INDEX_ATTR = _element_index
    LIST_ATTR = _feature_types{}
    ATTR_ACCUM_MODE = Merge List Attributes
    ATTR_CONFLICT_RES = Use List Attribute Values
    ELEMENTS -> FeatureMerger_met_html_content [REQUESTOR]
Note: EXCEL_LOG_WRITER : ALL_PRE_CSV_WRITE
Junction_23
    -> Junction_24
FeatureMerger_met_html_content
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeCreator_System_Bijlage
    UNUSED_SUPPLIER -> FeatureMerger_destination_dir [REQUESTOR]

Bookmark: OVerzicht per productgroep
AttributeManager_5
    ATTR_TABLE:
      SET_TO _aantal_bonregels (uint8) = FME_CONDITIONAL:DEFAULT_VALUE'_FME_NO_OP_'BOOL_OP;OR;COMPOSITE_TEST;1;TEST @Value(_artikel_regel) = 0'0'FME_NUM_CONDITIONS2___
      SET_TO IndexatieProcent (real64) = @Value(Indexatie)
    -> StatisticsCalculator_INDEXATIE_3
StatisticsCalculator_INDEXATIE_3
    ATTR_ACCUM_MODE = One
    CALCULATION_MODE = NUMERIC
    FEAT_STATS = IndexatieBedragBTW,NUMERIC_MODE,,,,SUM,,,,,,,,,;IndexatieBedragExBTW,NUMERIC_MODE,,,,SUM,,,,VALUE_COUNT,,,,,;Factuur nummer,NUMERIC_MODE,,,COUNT,,,,,,,,,,;FactuurRegel.Bedrag excl. Btw,NUMERIC_MODE,,,,SUM,,,,,,,,,;FactuurRegel.Bedrag Btw,NUMERIC_MODE,,,,SUM,,,,,,,,,;_aantal_bonregels,NUMERIC_MODE,,,,SUM,,,,,,,,,;_artikel_regel,NUMERIC_MODE,,,,SUM,,,,,,,,,;_index_regel,NUMERIC_MODE,,,,SUM,,,,,,,,,
    GROUP_BY = Productgroep Week "Factuur nummer"
    SUMMARY -> StatisticsCalculator_INDEXATIE_4
StatisticsCalculator_INDEXATIE_4
    ATTR_ACCUM_MODE = One
    CALCULATION_MODE = NUMERIC
    FEAT_STATS = IndexatieBedragExBTW.sum,NUMERIC_MODE,,,,SUM,,,,,,,,,;IndexatieBedragBTW.sum,NUMERIC_MODE,,,,SUM,,,,,,,,,;Factuur nummer.total_count,NUMERIC_MODE,,,,SUM,,,,,,,,,;Factuur nummer,NUMERIC_MODE,,,COUNT,,,,,,,,,,;IndexatieBedragExBTW.value_count,NUMERIC_MODE,,,,SUM,,,,,,,,,;FactuurRegel.Bedrag excl. Btw.sum,NUMERIC_MODE,,,,SUM,,,,,,,,,;FactuurRegel.Bedrag Btw.sum,NUMERIC_MODE,,,,SUM,,,,,,,,,;_aantal_bonregels.sum,NUMERIC_MODE,,,,SUM,,,,,,,,,;_artikel_regel.sum,NUMERIC_MODE,,,,SUM,,,,,,,,,;_index_regel.sum,NUMERIC_MODE,,,,SUM,,,,,,,,,
    GROUP_BY = Productgroep Week
    SUMMARY -> AttributeManager_4
AttributeManager_4
    ATTR_TABLE:
      RENAME_SET_VALUE Factuur nummer.total_count > _aantal_facturen (uint64)
      RENAME_SET_VALUE FactuurRegel.Bedrag excl. Btw.sum.sum > Subtotaal excl. Btw (real64) = FME_CONDITIONAL:DEFAULT_VALUE'_FME_NO_OP_'BOOL_OP;OR;COMPOSITE_TEST;1;TEST IndexatieBedragExBTW.sum.sum NOT_ATTRIBUTE_VALUE_NULL _FME_BLANK_STRING_'@Evaluate(@Value(Subtotaal excl. Btw)-@Value(IndexatieBedragExBTW.sum.sum))'FME_NUM_CONDITIONS2___
      RENAME_SET_VALUE IndexatieBedragExBTW.sum.sum > IndexatieBedragExBTW (real64) = FME_CONDITIONAL:DEFAULT_VALUE'_FME_NO_OP_'BOOL_OP;OR;COMPOSITE_TEST;1;TEST IndexatieBedragExBTW ATTRIBUTE_VALUE_NULL _FME_BLANK_STRING_'0'FME_NUM_CONDITIONS2___
      RENAME_SET_VALUE FactuurRegel.Bedrag Btw.sum.sum > Subtotaal Btw (real64) = FME_CONDITIONAL:DEFAULT_VALUE'_FME_NO_OP_'BOOL_OP;OR;COMPOSITE_TEST;1;TEST IndexatieBedragBTW.sum.sum NOT_ATTRIBUTE_VALUE_NULL _FME_BLANK_STRING_'@Evaluate(@Value(Subtotaal Btw)-@Value(IndexatieBedragBTW.sum.sum))'FME_NUM_CONDITIONS2___
      RENAME_SET_VALUE IndexatieBedragBTW.sum.sum > IndexatieBedragBTW (real64) = FME_CONDITIONAL:DEFAULT_VALUE'_FME_NO_OP_'BOOL_OP;OR;COMPOSITE_TEST;1;TEST IndexatieBedragBTW ATTRIBUTE_VALUE_NULL _FME_BLANK_STRING_'0'FME_NUM_CONDITIONS2___
      REMOVE Factuur nummer.total_count.sum (real64)
      REMOVE IndexatieBedragExBTW.value_count.sum (real64)
      RENAME_SET_VALUE _aantal_bonregels.sum.sum > _aantal_bonregels (real64)
      RENAME_SET_VALUE _artikel_regel.sum.sum > _aantal_artikel_regels (real64)
      RENAME_SET_VALUE _index_regel.sum.sum > _aantal_artikel_indexregels (real64)
      SET_TO TotaalExBTW (real64) = @Evaluate(@Value(IndexatieBedragExBTW)+@Value(Subtotaal excl. Btw))
      SET_TO TotaalBTW (real64) = @Evaluate(@Value(Subtotaal Btw)+@Value(IndexatieBedragBTW))
    -> AttributeRounder
AttributeRounder
    PLACES = 2
    ROUND_TYPE_TCL = round
    SRC_ATTRS = IndexatieBedragBTW IndexatieBedragExBTW Subtotaal Btw Subtotaal excl. Btw _aantal_artikel_indexregels _aantal_facturen TotaalBTW TotaalExBTW
    ROUND_TYPE = Nearest
    -> FeatureMerger_INDEXATIE [REQUESTOR]
AttributeKeeper_6
    CREATE_BULK_MODE_FEATURES = NO
    KEEP_ATTRS = Indexatie,Naam,Week
    -> FeatureMerger_INDEXATIE [SUPPLIER]
FeatureMerger_INDEXATIE
    ATTR_ACCUM_MODE = Merge Supplier
    ATTR_CONFLICT_RES_LOOKUP = SUPPLIER_IF_CONFLICT
    IGNORE_NULLS = No
    JOIN_KEYS = @Value(Productgroep) @Value(Naam) AUTO @Value(Week) @Value(Week) AUTO
    MERGE_TYPE_VAL = ATTRIBUTES
    PROCESS_DUPS = NO
    REJECT_NULL_MISSING_KEYS = No
    SUPPLIERS_FIRST = No
    ATTR_CONFLICT_RES = Use Supplier
    MERGE_TYPE = Attributes Only
    MERGED -> AttributeManager_10
    UNMERGED_REQUESTOR -> AttributeManager_10
AttributeManager_10
    ATTR_TABLE = SET_TO Indexatie (number(20,10)) = FME_CONDITIONAL:DEFAULT_VALUE'_FME_NO_OP_'BOOL_OP;OR;COMPOSITE_TEST;1;TEST Indexatie ATTRIBUTE_IS_MISSING _FME_BLANK_STRING_'0'FME_NUM_CONDITIONS2___
    -> Sorter_3
Sorter_3
    SORT_PARM = Productgroep NATURAL ASCENDING NON_VALUES_AFTER_VALUES Week NATURAL ASCENDING NON_VALUES_AFTER_VALUES
    SORTED -> Junction_7
Junction_7
    -> StatisticsCalculator_TOTALEN
    -> NumberSeparator__IndexatieBedragBTW
Junction_4
    -> Sorter_volgorde

Bookmark: Indexatie totalen
Note: AttributeManager_INDEX_regel : Output
Junction_11
    -> StatisticsCalculator_INDEXATIE
StatisticsCalculator_INDEXATIE
    ATTR_ACCUM_MODE = One
    CALCULATION_MODE = NUMERIC
    FEAT_STATS = IndexatieBedragExBTW,NUMERIC_MODE,,,,SUM,,,,,,,,,;IndexatieBedragBTW,NUMERIC_MODE,,,,SUM,,,,,,,,,;Factuur nummer,NUMERIC_MODE,,,COUNT,,,,,,,,,,
    GROUP_BY = "Factuur nummer"
    SUMMARY -> StatisticsCalculator_INDEXATIE_2
StatisticsCalculator_INDEXATIE_2
    ATTR_ACCUM_MODE = None
    CALCULATION_MODE = NUMERIC
    FEAT_STATS = IndexatieBedragExBTW.sum,NUMERIC_MODE,,,,SUM,,,,,,,,,;IndexatieBedragBTW.sum,NUMERIC_MODE,,,,SUM,,,,,,,,,;Factuur nummer.total_count,NUMERIC_MODE,,,,SUM,,,,,,,,,;Factuur nummer,NUMERIC_MODE,,,COUNT,,,,,,,,,,
    SUMMARY -> AttributeRounder_5
AttributeRounder_5
    PLACES = 2
    ROUND_TYPE_TCL = round
    SRC_ATTRS = IndexatieBedragBTW.sum.sum IndexatieBedragExBTW.sum.sum
    ROUND_TYPE = Nearest
    -> AttributeManager_3
AttributeManager_3
    ATTR_TABLE:
      RENAME_SET_VALUE Factuur nummer.total_count.sum > IndexatieRegels (real64)
      RENAME_SET_VALUE Factuur nummer.total_count > FacturenMetIndexatie (uint64)
      RENAME_SET_VALUE IndexatieBedragExBTW.sum.sum > Bedrag (real64)
      RENAME_SET_VALUE IndexatieBedragBTW.sum.sum > BTW bedrag regel (real64)
    USER_EXPOSED_ATTRIBUTES = IndexatieBedragExBTW.sum.sum,IndexatieBedragBTW.sum.sum,Bedrag.sum.sum,BTW bedrag regel.sum.sum
    -> NumberSeparator_3
NumberSeparator_3
    NumberSeparatorPrefix = €
    NumberSeparatorSeparatorChar = comma
    ToBeCreated = TotaalBedragExcl
    _AREA = @Value(Bedrag)
    -> NumberSeparator_4
NumberSeparator_4
    NumberSeparatorPrefix = €
    NumberSeparatorSeparatorChar = comma
    ToBeCreated = TotaalBedragBTW
    _AREA = @Value(BTW bedrag regel)
    -> StringReplacer_4
StringReplacer_4
    CASE = NO
    FIND_TEXT = .
    NO_MATCH = _FME_NO_OP_
    REGEXP = NO
    REPLACE_TEXT = #
    SRC_ATTRS = TotaalBedragBTW,TotaalBedragExcl
    -> StringReplacer_5
StringReplacer_5
    CASE = NO
    FIND_TEXT = ,
    NO_MATCH = _FME_NO_OP_
    REGEXP = NO
    REPLACE_TEXT = .
    SRC_ATTRS = TotaalBedragBTW,TotaalBedragExcl
    -> StringReplacer_6
StringReplacer_6
    CASE = NO
    FIND_TEXT = #
    NO_MATCH = _FME_NO_OP_
    REGEXP = NO
    REPLACE_TEXT = ,
    SRC_ATTRS = TotaalBedragBTW,TotaalBedragExcl
    -> AttributeCreator_html_2
AttributeCreator_html_2
    ATTR_TABLE:
      SET_TO html_content (varchar(200)) = <h4>Indexatie bedragen (opgenomen in totaal)</h4>
        <table  border=1>
           <thead>
              <tr>
                 <th>Facturen</th>
                 <th>Factuurregels</th>
                 <th>Indexatie bedrag (excl.)</th>
                 <th>Indexatie BTW</th>
              </tr>
           </thead>
           <tbody>
              <tr>
                 <td>@Value(FacturenMetIndexatie)</td>
                 <td>@Value(IndexatieRegels)</td>
                 <td>@Value(TotaalBedragExcl)</td>
                 <td>@Value(TotaalBedragBTW)</td>
              </tr>
           </tbody>
        </table>
    -> Sorter_volgorde

Bookmark: OVERZICHTEN PER Productgroep
NumberSeparator__IndexatieBedragBTW
    NumberSeparatorPrefix = €
    NumberSeparatorSeparatorChar = comma
    ToBeCreated = _IndexatieBedragBTW
    _AREA = @Value(IndexatieBedragBTW)
    -> NumberSeparator__IndexatieBedragExBTW
NumberSeparator__IndexatieBedragExBTW
    NumberSeparatorPrefix = €
    NumberSeparatorSeparatorChar = comma
    ToBeCreated = _IndexatieBedragExBTW
    _AREA = @Value(IndexatieBedragExBTW)
    -> NumberSeparator__SubtotaalBTW
NumberSeparator__SubtotaalBTW
    NumberSeparatorPrefix = €
    NumberSeparatorSeparatorChar = comma
    ToBeCreated = _SubtotaalBTW
    _AREA = @Value(Subtotaal Btw)
    -> NumberSeparator__SubtotaalExBTW
NumberSeparator__SubtotaalExBTW
    NumberSeparatorPrefix = €
    NumberSeparatorSeparatorChar = comma
    ToBeCreated = _SubtotaalExBTW
    _AREA = @Value(Subtotaal excl. Btw)
    -> NumberSeparator__TotaalExBTW
NumberSeparator__TotaalExBTW
    NumberSeparatorPrefix = €
    NumberSeparatorSeparatorChar = comma
    ToBeCreated = _TotaalExBTW
    _AREA = @Value(TotaalExBTW)
    -> NumberSeparator__TotaalBTW
NumberSeparator__TotaalBTW
    NumberSeparatorPrefix = €
    NumberSeparatorSeparatorChar = comma
    ToBeCreated = _TotaalBTW
    _AREA = @Value(TotaalBTW)
    -> StringReplacer_7
StringReplacer_7
    CASE = NO
    FIND_TEXT = .
    NO_MATCH = _FME_NO_OP_
    REGEXP = NO
    REPLACE_TEXT = #
    SRC_ATTRS = IndexatieBedragBTW,IndexatieBedragExBTW,Subtotaal Btw,Subtotaal excl. Btw,TotaalBTW,TotaalExBTW,_IndexatieBedragBTW,_IndexatieBedragExBTW,_SubtotaalBTW,_SubtotaalExBTW,_TotaalBTW,_TotaalExBTW
    -> StringReplacer_8
StringReplacer_8
    CASE = NO
    FIND_TEXT = ,
    NO_MATCH = _FME_NO_OP_
    REGEXP = NO
    REPLACE_TEXT = .
    SRC_ATTRS = IndexatieBedragBTW,IndexatieBedragExBTW,Subtotaal Btw,Subtotaal excl. Btw,TotaalBTW,TotaalExBTW,_IndexatieBedragBTW,_IndexatieBedragExBTW,_SubtotaalBTW,_SubtotaalExBTW,_TotaalBTW,_TotaalExBTW
    -> StringReplacer_9
StringReplacer_9
    CASE = NO
    FIND_TEXT = #
    NO_MATCH = _FME_NO_OP_
    REGEXP = NO
    REPLACE_TEXT = ,
    SRC_ATTRS = IndexatieBedragBTW,IndexatieBedragExBTW,Subtotaal Btw,Subtotaal excl. Btw,TotaalBTW,TotaalExBTW,_IndexatieBedragBTW,_IndexatieBedragExBTW,_SubtotaalBTW,_SubtotaalExBTW,_TotaalBTW,_TotaalExBTW
    -> AttributeCreator_html_3
AttributeCreator_html_3
    ATTR_TABLE:
      SET_TO html_bedragen (varchar(200)) =       <tr>
                 <td>@Value(Productgroep)</td>
                 <td>@Value(Week)</td>
                 <td>@Value(Indexatie)</td>
                 <td>@Value(_SubtotaalExBTW)</td>
                 <td>@Value(_IndexatieBedragExBTW)</td>
                 <td>@Value(_SubtotaalBTW)</td>
                 <td>@Value(_IndexatieBedragBTW)</td>
                 <td>@Value(_TotaalExBTW)</td>
                 <td>@Value(_TotaalBTW)</td>
              </tr>
      SET_TO html_aantallen (varchar(200)) =       <tr>
                 <td>@Value(Productgroep)</td>
                 <td>@Value(Week)</td>
                 <td>@Value(_aantal_facturen)</td>
                 <td>@Value(_aantal_bonregels)</td>
                 <td>@Value(_aantal_artikel_regels)</td>
                 <td>@Value(_aantal_artikel_indexregels)</td>
              </tr>
    -> AttributeCombiner_2
AttributeCombiner_2
    ATTRS = html_aantallen html_bedragen
    DROP_EMPTY = No
    QUOT = None
    -> AttributeCreator_html_5
AttributeCreator_html_5
    ATTR_TABLE:
      SET_TO html_content (varchar(200)) = <h4>Bedragen per productgroep </h4>
        <table border=1>
           <thead>
              <tr>
                 <th>Productgroep</th>
                 <th>Week</th>
                 <th>Indexatie (%)</th>
                 <th>Subtotaal ex BTW</th>
                 <th>Indexatie ex BTW</th>
                 <th>Subtotaal BTW</th>
                 <th>Indexatie BTW</th>
                 <th>Totaal ex BTW</th>
                 <th>Totaal BTW</th>
              </tr>
           </thead>
           <tbody>
        @Value(html_bedragen)
           </tbody>
        </table>
        <h4>Aantallen per productgroep </h4>
        <table border=1>
           <thead>
              <tr>
                 <th>Productgroep</th>
                 <th>Week</th>
                 <th>#Facturen</th>
                 <th>#Bonregels</th>
                 <th>#Artikelregels</th>
                 <th>#Indexatieregels</th>
              </tr>
           </thead>
           <tbody>
        @Value(html_aantallen)
           </tbody>
        </table>
      SET_TO Volgorde (uint8) = 31
    -> Junction_4

Bookmark: TOTAALRegel
StatisticsCalculator_TOTALEN
    ATTR_ACCUM_MODE = None
    CALCULATION_MODE = NUMERIC
    FEAT_STATS = Subtotaal excl. Btw,NUMERIC_MODE,,,,SUM,,,,,,,,,;IndexatieBedragExBTW,NUMERIC_MODE,,,,SUM,,,,,,,,,;Subtotaal Btw,NUMERIC_MODE,,,,SUM,,,,,,,,,;IndexatieBedragBTW,NUMERIC_MODE,,,,SUM,,,,,,,,,;TotaalExBTW,NUMERIC_MODE,,,,SUM,,,,,,,,,;TotaalBTW,NUMERIC_MODE,,,,SUM,,,,,,,,,
    SUMMARY -> AttributeRounder_2
AttributeRounder_2
    PLACES = 2
    ROUND_TYPE_TCL = round
    SRC_ATTRS = IndexatieBedragBTW.sum IndexatieBedragExBTW.sum Subtotaal Btw.sum Subtotaal excl. Btw.sum TotaalBTW.sum TotaalExBTW.sum
    ROUND_TYPE = Nearest
    -> NumberSeparator__I_SubtotaalEx
NumberSeparator__I_SubtotaalEx
    NumberSeparatorPrefix = €
    NumberSeparatorSeparatorChar = comma
    ToBeCreated = _SubtotaalExBTW
    _AREA = @Value(Subtotaal excl. Btw.sum)
    -> NumberSeparator__IndexatieBedragExBTW_2
NumberSeparator__IndexatieBedragExBTW_2
    NumberSeparatorPrefix = €
    NumberSeparatorSeparatorChar = comma
    ToBeCreated = _IndexatieBedragExBTW
    _AREA = @Value(IndexatieBedragExBTW.sum)
    -> NumberSeparator__SubtotaalBTW_2
NumberSeparator__SubtotaalBTW_2
    NumberSeparatorPrefix = €
    NumberSeparatorSeparatorChar = comma
    ToBeCreated = _SubtotaalBTW
    _AREA = @Value(Subtotaal Btw.sum)
    -> NumberSeparator_IndexatieBedragBTW
NumberSeparator_IndexatieBedragBTW
    NumberSeparatorPrefix = €
    NumberSeparatorSeparatorChar = comma
    ToBeCreated = _IndexatieBedragBTW
    _AREA = @Value(IndexatieBedragBTW.sum)
    -> NumberSeparator__TotaalExBTW_2
NumberSeparator__TotaalExBTW_2
    NumberSeparatorPrefix = €
    NumberSeparatorSeparatorChar = comma
    ToBeCreated = _TotaalExBTW
    _AREA = @Value(TotaalExBTW.sum)
    -> NumberSeparator___TotaalBTW
NumberSeparator___TotaalBTW
    NumberSeparatorPrefix = €
    NumberSeparatorSeparatorChar = comma
    ToBeCreated = _TotaalBTW
    _AREA = @Value(TotaalBTW.sum)
    -> StringReplacer_10
StringReplacer_10
    CASE = NO
    FIND_TEXT = .
    NO_MATCH = _FME_NO_OP_
    REGEXP = NO
    REPLACE_TEXT = #
    SRC_ATTRS = _IndexatieBedragBTW,_IndexatieBedragExBTW,_SubtotaalBTW,_SubtotaalExBTW,_TotaalBTW,_TotaalExBTW
    -> StringReplacer_11
StringReplacer_11
    CASE = NO
    FIND_TEXT = ,
    NO_MATCH = _FME_NO_OP_
    REGEXP = NO
    REPLACE_TEXT = .
    SRC_ATTRS = _IndexatieBedragBTW,_IndexatieBedragExBTW,_SubtotaalBTW,_SubtotaalExBTW,_TotaalBTW,_TotaalExBTW
    -> StringReplacer_12
StringReplacer_12
    CASE = NO
    FIND_TEXT = #
    NO_MATCH = _FME_NO_OP_
    REGEXP = NO
    REPLACE_TEXT = ,
    SRC_ATTRS = _IndexatieBedragBTW,_IndexatieBedragExBTW,_SubtotaalBTW,_SubtotaalExBTW,_TotaalBTW,_TotaalExBTW
    -> AttributeCreator_html_4
AttributeCreator_html_4
    ATTR_TABLE:
      SET_TO html_content (varchar(200)) = <h4>Totalisering</h4>
        <table border=1>
           <thead>
              <tr>
                 <th>Subtotaal ex BTW</th>
                 <th>Indexatie ex BTW</th>
                 <th>Subtotaal BTW</th>
                 <th>Indexatie BTW</th>
                 <th>Totaal ex BTW</th>
                 <th>Totaal BTW</th>
              </tr>
           </thead>
           <tbody>
              <tr>
                 <td>@Value(_SubtotaalExBTW)</td>
                 <td>@Value(_IndexatieBedragExBTW)</td>
                 <td>@Value(_SubtotaalBTW)</td>
                 <td>@Value(_IndexatieBedragBTW)</td>
                 <td>@Value(_TotaalExBTW)</td>
                 <td>@Value(_TotaalBTW)</td>
              </tr>
           </tbody>
        </table>

      SET_TO Volgorde (uint8) = 41
    -> Junction_4

Bookmark: LEES CSV Template
FeatureReader_FMUTA6_Schema
    ATTRIBUTES = CSV,"Regelnummer,Dagboekcode,Dagboeknummer,Periode,""nvt (1)"",Factuurnummer,Factuuregelomschrijving,Factuurdatum,Grootboekrekening,Debiteurnummer,Referentie,Valuta,Bedrag,Aantal,Eenheid,Tarief,Artikelomschrijving,""nvt (6)"",""Vervaldatum factuur"",""Vervaldatum KB"",BTWsoort,""BTW bedrag regel"""
    ATTR_ACCUM_MODE = Only Use Result
    CLIP_TO_ENVELOPE = NO
    COMBINE_GEOM = Use Result
    CSV2_CASE_SENSITIVE_FIELD_NAMES = Yes
    CSV2_CHUNK_SIZE = 100000
    CSV2_DATA_START_LINE = 2
    CSV2_DATE_INPUT_FORMAT = ISO
    CSV2_DELIMITER = auto
    CSV2_DELIMITER_DETECTION_ALGORITHM = EQUAL_FIELDS_PER_LINE
    CSV2_ENCODING = windows-1252
    CSV2_ENFORCE_STRICT_SCHEMA = No
    CSV2_EXPLICIT_GEOMETRY_ATTRIBUTES = Yes
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TRIM_FIELD_VALUE_WHITESPACE = No
    CSV2_TYPE_ATTRIBUTE_HANDLING = STANDARD_TYPES
    CSV2_USE_CUSTOM_SCHEMA = NO
    DATASET = @Value(CSV_Schema)
    FEATURETYPES = CSV
    FORMAT = CSV2
    INITIATOR_FIRST_OUTPUT = default
    INPUT_PORT_INITIATOR_CONNECTED = CONNECTED
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    <SCHEMA> -> AttributeKeeper

Bookmark: DEBUG
EXCEL_LOG_WRITER: FeatureWriter
    CONFIG_PARAMETERS = ESCAPE_COMMAS_IN_FTP_FORMAT_PARAMETERS,no
    DATASET = @Value(LogBestand)
    DATASET_ATTR = _dataset
    FEATURE_TYPE_LIST_ATTR = _feature_types
    FORMAT = XLSXW
    TOTAL_FEATURES_WRITTEN_ATTR = _total_features_written
    XLSXW_ALWAYS_CREATE_FEATURE_TYPES = NO
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = NO
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = No
    XLSXW_WRITER_MODE = Insert

Bookmark: LEES Debiteuren
HTTPCaller_IW_DataConnector
    AUTH_METHOD_TYPE = NC
    AUTH_NAMED_CONNECTION = IW_DataConnector_Debiteuren
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    RETRY_FAILED_TRANSFERS = CONNECTION 429 500 501 502 503 504 505 506 507 508 509 510 511
    RETRY_INITIAL_BACKOFF = 5000
    RETRY_MAX_RETRIES = 3
    SPLIT_MULTIPART_DOWNLOADS = NO
    STATUS_CODE_ATTR = _http_status_code
    TARGET_ATTR = _response_body
    TARGET_ATTR_ENCODING = auto-detect
    TARGET_URL = @Value(_url_IW_DataConnector)
    TRANSFER_TIMEOUT_LENGTH = 90
    USE_COOKIES = No
    VERIFY_SSL_CERTIFICATES = Yes
    AUTH_METHOD = Web Connection
    -> JSONFragmenter
    <REJECTED> -> AttributeCreator_log_message_3
AttributeCreator_log_message_3
    ATTR_TABLE:
      SET_TO _log_message (varchar(200)) = <font color=red>Foutmelding</font> HTTPCaller IW Dataconnector: @Value(_http_status_code) : @Value(_response_body)
      SET_TO _log_volgorde (uint8) = 21
    INPUT_PORT_CONNECTED = CONNECTED
    -> AttributeKeeper_9

Bookmark: LOg messages
AttributeKeeper_9
    CREATE_BULK_MODE_FEATURES = NO
    KEEP_ATTRS = _log_message,_log_volgorde
    -> Sorter
Sorter
    SORT_PARM = _log_volgorde NATURAL ASCENDING NON_VALUES_AFTER_VALUES
    SORTED -> AttributeCombiner_7
AttributeCombiner_7
    ATTRS = _log_message
    DELIM = <br>
    DROP_EMPTY = No
    QUOT = None
    -> AttributeCreator_html_15
AttributeCreator_html_15
    ATTR_TABLE:
      SET_TO html_content (varchar(200)) = @Value(_log_message)
      SET_TO Volgorde (uint8) = 0
    -> Junction_4

Bookmark: Sorteren en samenvoegen html_content t.b.v. rapportage
Sorter_volgorde
    SORT_PARM = Volgorde NATURAL ASCENDING NON_VALUES_AFTER_VALUES
    SORTED -> AttributeCombiner
AttributeCombiner
    ATTRS = html_content
    DROP_EMPTY = No
    PREFIX = <hr>
    QUOT = None
    SUFFIX = <br><br>
    -> FeatureMerger_met_html_content [SUPPLIER]

Bookmark: Mailen
AttributeCreator_System_Bijlage
    ATTR_TABLE = SET_TO Bijlage (varchar(200)) = FME_CONDITIONAL:DEFAULT_VALUE'@Value(destination_dir)/@Value(name).csv'BOOL_OP;OR;COMPOSITE_TEST;1;TEST $(FME_OS) = Wndows'@Value(destination_dir)\@Value(name).csv'FME_NUM_CONDITIONS2___
    -> StringReplacer_newlines
StringReplacer_newlines
    CASE = NO
    NO_MATCH = _FME_NO_OP_
    REGEXP = NO
    STR_REPLACE_TABLE = "html_content \n "
    -> TestFilter_FME_OS
    -> AttributeCreator_filecopy_source_dataset
    -> AttributeCreator_filecopy_source_dataset_3
TestFilter_FME_OS
    DEFAULT_VALUE = FME Flow
    PASSED_TEST_GROUP_OUTPUT = FIRST
    TEST_LIST = "BOOL_OP,OR,COMPOSITE_TEST,""""""1"""""",TEST_CLAUSE,TEST $(FME_OS) = Windows",Windows = local
    Windows = local -> GKB_EmailGenerator_local_zonder_bijlage
    FME Flow -> GKB_EmailGenerator
GKB_EmailGenerator_local_zonder_bijlage
    Body = @Value(html_content)
    Subject = $(_zone_timestamp)
    To = $(ResultaatEmail)
    VERZAMEL_MAIL = YES
GKB_EmailGenerator
    ATTACHMENT = @Value(Bijlage)
    Body = @Value(html_content)
    CC = dirkjan@gkbgroep.nl
    Subject = FMUTA6 Conversie Facturen $(_zone_timestamp)
    To = $(ResultaatEmail)
    VERZAMEL_MAIL = YES

Bookmark: COPY en input bestanden naar runmap
AttributeCreator_filecopy_source_dataset_3
    ATTR_TABLE = SET_TO filecopy_source_dataset (varchar(200)) = @Value(destination_dir)\log_FMUTA6_factuur_$(_zone_timestamp).html
    INPUT_PORT_CONNECTED = CONNECTED
    -> FeatureWriter_html_log [HTML]
FeatureWriter_html_log
    CONFIG_PARAMETERS = ESCAPE_COMMAS_IN_FTP_FORMAT_PARAMETERS,no
    DATASET = @Value(filecopy_source_dataset)
    DATASET_ATTR = _dataset
    FEATURE_TYPE_LIST_ATTR = _feature_types
    FORMAT = HTML
    HTML_COORDINATE_SYSTEM_GRANULARITY = FEATURE
    HTML_DESTINATION_DATASETTYPE_VALIDATION = Yes
    HTML_ENCODING = UTF8
    HTML_END_OF_LINE = System
    HTML_MIME_TYPE = text/html
    HTML_OVERWRITE_FILE = YES
    HTML_WRITE_LAST_EOL = YES
    HTML_WRITE_UTF8_BOM = YES
    MORE_SUMMARY_ATTRS = destination_dir
    TOTAL_FEATURES_WRITTEN_ATTR = _total_features_written
    SUMMARY -> FeatureWriter_COPY_HTML_LOG [Summary]
FeatureWriter_COPY_HTML_LOG
    CONFIG_PARAMETERS = ESCAPE_COMMAS_IN_FTP_FORMAT_PARAMETERS,no
    DATASET = @Value(_feature_types{0}.destination_dir)
    DATASET_ATTR = _dataset
    FEATURE_TYPE_LIST_ATTR = _feature_types
    FILECOPY_COORDINATE_SYSTEM_GRANULARITY = FEATURE
    FILECOPY_COPY_SOURCE_DIRECTORY = NO
    FILECOPY_COPY_SUBDIRECTORIES = NO
    FILECOPY_DESTINATION_DATASETTYPE_VALIDATION = Yes
    FILECOPY_FAIL_INVALID_DESTINATION = NO
    FILECOPY_FAIL_NONEXISTENT_SOURCE = NO
    FILECOPY_FEATURE_TYPE_NAMES_AS_FOLDERS = NO
    FILECOPY_FILE_OPERATION = COPY
    FILECOPY_MIME_TYPE = application/vnd.openxmlformats-officedocument.spreadsheetml.sheet
    FILECOPY_OVERWRITE_FILE = YES
    FORMAT = FILECOPY
    TOTAL_FEATURES_WRITTEN_ATTR = _total_features_written
AttributeCreator_filecopy_source_dataset
    ATTR_TABLE = SET_TO filecopy_source_dataset (varchar(200)) = $(Factuur_XLSX)
    INPUT_PORT_CONNECTED = CONNECTED
    -> FeatureWriter_COPY_FACTUUR_XLSX [Summary]
FeatureWriter_COPY_FACTUUR_XLSX
    CONFIG_PARAMETERS = ESCAPE_COMMAS_IN_FTP_FORMAT_PARAMETERS,no
    DATASET = @Value(destination_dir)
    DATASET_ATTR = _dataset
    FEATURE_TYPE_LIST_ATTR = _feature_types
    FILECOPY_COORDINATE_SYSTEM_GRANULARITY = FEATURE
    FILECOPY_COPY_SOURCE_DIRECTORY = NO
    FILECOPY_COPY_SUBDIRECTORIES = NO
    FILECOPY_DESTINATION_DATASETTYPE_VALIDATION = Yes
    FILECOPY_FAIL_INVALID_DESTINATION = NO
    FILECOPY_FAIL_NONEXISTENT_SOURCE = NO
    FILECOPY_FEATURE_TYPE_NAMES_AS_FOLDERS = NO
    FILECOPY_FILE_OPERATION = COPY
    FILECOPY_MIME_TYPE = application/vnd.openxmlformats-officedocument.spreadsheetml.sheet
    FILECOPY_OVERWRITE_FILE = YES
    FORMAT = FILECOPY
    MORE_SUMMARY_ATTRS = destination_dir
    TOTAL_FEATURES_WRITTEN_ATTR = _total_features_written
    SUMMARY -> AttributeCreator_filecopy_source_dataset_2
AttributeCreator_filecopy_source_dataset_2
    ATTR_TABLE = SET_TO filecopy_source_dataset (varchar(200)) = $(Bonnen_XLSX)
    INPUT_PORT_CONNECTED = CONNECTED
    -> FeatureWriter_COPY_BON_XLSX [Summary]
FeatureWriter_COPY_BON_XLSX
    CONFIG_PARAMETERS = ESCAPE_COMMAS_IN_FTP_FORMAT_PARAMETERS,no
    DATASET = @Value(_feature_types{0}.destination_dir)
    DATASET_ATTR = _dataset
    FEATURE_TYPE_LIST_ATTR = _feature_types
    FILECOPY_COORDINATE_SYSTEM_GRANULARITY = FEATURE
    FILECOPY_COPY_SOURCE_DIRECTORY = NO
    FILECOPY_COPY_SUBDIRECTORIES = NO
    FILECOPY_DESTINATION_DATASETTYPE_VALIDATION = Yes
    FILECOPY_FAIL_INVALID_DESTINATION = NO
    FILECOPY_FAIL_NONEXISTENT_SOURCE = NO
    FILECOPY_FEATURE_TYPE_NAMES_AS_FOLDERS = NO
    FILECOPY_FILE_OPERATION = COPY
    FILECOPY_MIME_TYPE = application/vnd.openxmlformats-officedocument.spreadsheetml.sheet
    FILECOPY_OVERWRITE_FILE = YES
    FORMAT = FILECOPY
    TOTAL_FEATURES_WRITTEN_ATTR = _total_features_written

Bookmark: PBA -> IW
Note: Velden CSV nodig vlgs import definitie IW : / Bonnummer = factuurexport / Ontvangstdatum = factuurexport / Werkorder = bonnenexport / Artikelnr = = factuurexport (leeglaten) / Artikelomschrijving = = factuurexport / Referentie = bonnenexport / Begeleidingsbrief = bonnenexport / Kenteken = bonnenexport / Aantal = factuurexport / Eenheid = factuurexport / Prijs = factuurexport / BTW indicatie = factuurexport / BTW indicatie / H = BTW hoog (=21) / L = BTW laag (=9) / V = BTW verlegd / N of N = BTW 0 (=0)

FME custom transformer AttributeCombiner
Combines specified attribute(s) of multiple features to form concatenated string(s). This transformer outputs a single feature for each group of input features, and the specified attribute(s) in the output feature will store the concatenated string(s). 
    This transformer always discards <null> and <missing> attributes. Regarding the empty string, you can control how to handle that with the "Drop Empty String" parameter. 
    The function is similar to the "Attributes to Concatenate" option of the Aggregator, but this transformer does not aggregate features. The geometry and unspecified attributes of any one feature for each group will be preserved, but others will be discarded. 
    This transformer can be used to concatenate specific attributes of many features efficiently, if you don't need to perform feature aggregation.
    Note: This transformer contains a Python script, which was tested with both Python 2.7 and Python 3.x interpreters.
Parameters
    Group By
    : 
    If you specify one or more attributes in this parameter, the concatenation will be performed for each group of features which have the same value(s) for the specified attribute(s).
    Input is Ordered by Group
    :
    If you are sure that the input features are sorted by the "Group By" attributes, you can set "Yes" to this parameter so that the processing will be performed with the best performance.
    Attributes to Combine
    :
    Select attributes that should be combined.
    Maximum Number of Features to Combine
    :
    Optionally you can specify the maximum number of features to combine into one. The number must be an integer greater than 0. Otherwise, the setting will be ignored. 
    Note that the number specified with this parameter indicates the maximum number of processed features at once. The number of concatenated attributes could be less than the maximum, since <null> and <missing> (and <empty> if you set "Yes" to the "Drop Empty String" parameter) attributes will be discarded. 
    Drop Empty String
    :
    By default, this transformer treats the empty string as a valid value which should be concatenated. If you don't want to concatenate empty strings, set "Yes" to this parameter.
    Delimiter String
    :
    Specify a character string that should be used as a delimiter string to separate individual values. You can also leave blank this parameter not to use any delimiter.
    Surround Each Value With
    :
    Optionally you can select a pair of symbols (e.g. single quotation marks) that will surround each value before concatenating. 
    Prefix for Each Value
    : 
    Optionally you can specify a prefix string that will be added to each value. 
    Suffix for Each Value
    : 
    Optionally you can specify a suffix string that will be added to each value.

Parameters:
- GROUP_BY =   # " " Group By
- ORDERED_BY_GROUP = No   # Input is Ordered by Group
- ATTRS =   # " " Attributes to Combine
- MAX_NUM =   # Maximum Number of Features to Combine
- DROP_EMPTY = No   # Drop Empty String
- DELIM = ,   # " " Delimiter String
- QUOT = None
- PREFIX =   # " " Prefix for Each Value
- SUFFIX =   # " " Suffix for Each Value

Input (input)
    -> ParameterFetcher
ParameterFetcher
    ATTR_LIST = __tmp.group_by $(GROUP_BY) __tmp.attrs $(ATTRS) __tmp.max_num $(MAX_NUM) __tmp.delim $(DELIM) __tmp.drop_empty $(DROP_EMPTY) __tmp.quot $(QUOT) __tmp.prefix $(PREFIX) __tmp.suffix $(SUFFIX)
    -> TclCaller
TclCaller
    NEW_ATTRIBUTES = __tmp.attr{}
    SRC:
      proc preProcessToCombine {} {
          set i 0
          foreach attr [FME_GetAttribute "__tmp.attrs"] {
              FME_SetAttribute "__tmp.attr{$i}" $attr
              incr i
          }
          set num [FME_GetAttribute "__tmp.max_num"]
          if {![string is integer -strict $num]} {
              FME_SetAttribute "__tmp.max_num" 0
          }
          set group {}
          foreach attr [FME_GetAttribute "__tmp.group_by"] {
              if {![FME_AttributeExists $attr]} {
                  lappend group "\a"
              } elseif {[FME_IsAttributeNull $attr]} {
                  lappend group "\b"
              } else {
                  lappend group [FME_GetAttribute $attr]
              }
          }
          return [join $group {_}]
      }
    TCLPROG = preProcessToCombine
    VAL_ATTR = __tmp.group
    -> Tester
Tester
    BOOL_OP = OR
    TEST_CLAUSE:
      TEST @Value(__tmp.group_by) = ""
      TEST $(ORDERED_BY_GROUP) = Yes
    TEST_MODE = Automatic
    PASSED -> PythonCaller
    FAILED -> Sorter
Sorter
    SORT_PARM = __tmp.group ALPHA ASCENDING
    SORTED -> PythonCaller
PythonCaller
    PYTHONSOURCE:
      # 2016-04-13, Takashi Iijima, Original Implementation
      # 2018-05-07, Takashi Iijima, Suuports Python 3.x
      # 2020-01-13, Takashi Iijima, Changed Default Python Interpreter to 3.6+, saved with FME 2017.1.2.1

      import fme
      import fmeobjects, locale

      class AttributeCombiner(object):
          def __init__(self):
              import platform
              vt = platform.python_version_tuple()
              if vt[0] == '2':
                  loc = locale.getdefaultlocale()
                  enc = loc[1] if loc else 'utf_8'
                  self.toStr = lambda s: s.encode(enc) if isinstance(s, unicode) else str(s)
              else:
                  self.toStr = lambda s: s
              self.reset(None, None)

          def reset(self, group, feature):
              self.group = group # group ID value
              self.feature = feature # first feature for each group
              self.data = {} # key: attribute name, value: list of attribute values
              self.count = 0 # counter for number of features to combine

          def input(self, feature):
              group = feature.getAttribute('__tmp.group')
              num = int(feature.getAttribute('__tmp.max_num'))
              if group != self.group or (0 < num and num <= self.count):
                  self.output()
                  self.reset(group, feature)
              for attr in feature.getAttribute('__tmp.attr{}'):
                  attr = self.toStr(attr)
                  isNull, isMissing, type = feature.getAttributeNullMissingAndType(attr)
                  if not isNull and not isMissing:
                      self.data.setdefault(attr, []).append('%s' % feature.getAttribute(attr))
              self.count += 1

          def close(self):
              self.output()

          def output(self):
              if self.feature:
                  fmt = self.getFormat()
                  delim = self.feature.getAttribute('__tmp.delim')
                  if self.feature.getAttribute('__tmp.drop_empty') == 'Yes':
                      for attr, values in self.data.items():
                          self.feature.setAttribute(attr, delim.join([fmt % v for v in values if v != '']))
                  else:
                      for attr, values in self.data.items():
                          self.feature.setAttribute(attr, delim.join([fmt % v for v in values]))
                  self.pyoutput(self.feature)

          def getFormat(self):
              formats = {
                  'Single': '\'%s%%s%s\'' ,
                  'Double': '"%s%%s%s"' ,
                  'Round': '(%s%%s%s)',
                  'Curly': '{%s%%s%s}',
                  'Square': '[%s%%s%s]',
                  'Inequality': '<%s%%s%s>',
                  'None': '%s%%s%s'
              }
              option = self.feature.getAttribute('__tmp.quot')
              prefix= self.feature.getAttribute('__tmp.prefix')
              suffix = self.feature.getAttribute('__tmp.suffix')
              return formats[option] % (prefix, suffix)
    PYTHONSYMBOL = AttributeCombiner
    -> AttributeRemover
AttributeRemover
    LIST_ATTRS = __tmp.attr{}
    REMOVE_ATTRS = __tmp.attrs,__tmp.delim,__tmp.drop_empty,__tmp.group,__tmp.group_by,__tmp.max_num,__tmp.prefix,__tmp.quot,__tmp.suffix
    -> Output (output)
Output (output)

FME workspace GKBY_Rdam_Substraat_Overzicht.fmw
Title: GKBY_RDam_Substraat_Overzicht

Parameters:
- Factuur_XLSX = C:\Users\dirkjan\OneDrive - GKB Groep\Projecten Realisatie\GKBY\RotterdamFacturatieSubstraten\Rotterdam factuurrun week 49-50.xlsx   # PBA Factuurrunbestand (.xlsx)
- Bonnen_XLSX = C:\Users\dirkjan\OneDrive - GKB Groep\Projecten Realisatie\GKBY\RotterdamFacturatieSubstraten\Rotterdam bonnen week 49-50.xlsx   # PBA Bonnenoverzicht (.xlsx)
- EMAILADRES = dirkjan@gkbgroep.nl   # Resultaat versturen aan (kommagescheiden)
- ArtikelTabel_XLSX = $(FME_SHAREDRESOURCE_DATA)/Grondbank/Substraten/ArtikelTabel.xlsx   # Artikeltabel (.xlsx)
- Template_XLSX = Invulblad afnames landschapsubstraten.xlsx   # Template invulblad RDAM (.xlsx)
- FME_SHAREDRESOURCE_DATA = C:\temp   # FME Flow Data Directory
- FME_SHAREDRESOURCE_TEMP = C:\temp   # FME Flow Temporary Resource Directory

Readers:
- XLSXR_1: XLSXR from $(Factuur_XLSX)
- XLSXR_2: XLSXR from $(Bonnen_XLSX)
- XLSXR_3: XLSXR from $(ArtikelTabel_XLSX)
- XLSXR_5: XLSXR from $(Template_XLSX)

Writers:
- FILECOPY_1: FILECOPY to Grondbank

Junction_5
    -> TestFilter_formulas_aanwezig
NoFeaturesTester_Bonnen
    NoInput -> AttributeCreator_LOGMESSAGE_Geen_bonnen_gelezen_log_volgorde_2
    -> FeatureCounter
NoFeaturesTester_Facturen
    NoInput -> AttributeCreator_LOGMESSAGE_Geen_bonnen_gelezen_log_volgorde_1
    -> DateTimeStamper_2
DateTimeStamper_2
    DATETIME_ATTR = _timestamp
    INCLUDE_FRAC_SECONDS = NO
    INCLUDE_OFFSET = YES
    SCOPE = translation
    STAMP_TYPE = datetime
    TIMEZONE = utc
    -> DateTimeCalculator_2
DateTimeCalculator_2
    DAYS = 0
    HOURS = 1
    MINUTES = 0
    MODE = DATETIMECALC_1_ADD_INTERVAL
    MONTHS = 0
    OPERATION_PARAMETERS = START_DATETIME_DATETIMECALC_1_ADD_INTERVAL]@Value(_timestamp)]OPERATOR]ADD]YEARS]0]MONTHS]0]DAYS]0]HOURS]1]MINUTES]0]SECONDS]0]RESULT_DATETIME]_result_datetime]START_DATETIME]@Value(_timestamp)
    OPERATOR = ADD
    RESULT_DATETIME = _result_datetime
    SECONDS = 0
    START_DATETIME = @Value(_timestamp)
    START_DATETIME_DATETIMECALC_1_ADD_INTERVAL = @Value(_timestamp)
    YEARS = 0
    -> AttributeCreator_2
AttributeCreator_2
    ATTR_TABLE:
      SET_TO DatumStamp (varchar(200)) = @DateTimeFormat(@Value(_result_datetime),%Y%m%d%H%M)
      SET_TO DoelPath (varchar(200)) = FME_CONDITIONAL:DEFAULT_VALUE'$(FME_SHAREDRESOURCE_DATA)Grondbank/Substraten/Factuurrun__@Value(DatumStamp)'BOOL_OP;OR;COMPOSITE_TEST;1;TEST $(FME_OS) = Windows'$(FME_SHAREDRESOURCE_DATA)\Grondbank\Substraten\Factuurrun_@Value(DatumStamp)'FME_NUM_CONDITIONS2___
      SET_TO ExcelDoelbestand (varchar(200)) = GKB_Invulblad_afnames_landschapsubstraten_week_@DateTimeFormat(@DateTimeNow(),%U)_@Value(DatumStamp).xlsx
      SET_TO ExcelDoelPath (varchar(200)) = FME_CONDITIONAL:DEFAULT_VALUE'@Value(DoelPath)/@Value(ExcelDoelbestand)'BOOL_OP;OR;COMPOSITE_TEST;1;TEST $(FME_OS) = Windows'@Value(DoelPath)\@Value(ExcelDoelbestand)'FME_NUM_CONDITIONS2___
      SET_TO DoelZip (varchar(200)) = FME_CONDITIONAL:DEFAULT_VALUE'@Value(DoelPath)/GKB_Bonnen_substraten_@Value(DatumStamp).zip'BOOL_OP;OR;COMPOSITE_TEST;1;TEST $(FME_OS) = Windows'@Value(DoelPath)\GKB_Bonnen_substraten_@Value(DatumStamp).zip'FME_NUM_CONDITIONS2___
    INPUT_PORT_CONNECTED = CONNECTED
    -> FeatureMerger_3 [SUPPLIER]
    -> FeatureCounter_2
UniqueValueLogger
    VAL = @Value(FactuurRegel.Artikel.Omschrijving)
FeatureMerger_ContractOmschrijving_aan_Factuur__Rejected_: Inspector [off]
Creator
    GEOMTYPE = Geometry Object
    NUM = 1
    CREATED -> AzureFileStorageConnector_List

Bookmark: LEES Bronnen
ArtikelTabel (reader XLSXR_3) [off]
    attributes: GKB_Artikel char(47), RDAM_Omschrijving char(29), Opmerking char(65)
Blad1 (reader XLSXR_5) [off]
    attributes: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
Creator_2
    GEOMTYPE = Geometry Object
    NUM = 1
    CREATED -> AttributeCreator
AttributeCreator
    ATTR_TABLE:
      SET_TO input (varchar(200)) = FME_CONDITIONAL:DEFAULT_VALUE'Input'BOOL_OP;OR;COMPOSITE_TEST;1;TEST $(FME_OS) = Windows'Input'FME_NUM_CONDITIONS2___
      SET_TO ArtikelTabel (varchar(17)) = ArtikelTabel.xlsx
      SET_TO Invulblad (varchar(48)) = Invulblad_afnames_landschapsubstraten.xlsx
    INPUT_PORT_CONNECTED = CONNECTED
    -> FeatureReader_2 [INITIATOR]
    -> FeatureReader [INITIATOR]
FeatureReader
    ATTRIBUTES = ArtikelTabel,"GKB_Artikel,RDAM_Omschrijving,Opmerking","ArtikelTabel test","GKB_Artikel,RDAM_Omschrijving,Opmerking"
    ATTR_ACCUM_MODE = Merge Initiator and Result
    ATTR_CONFLICT_RES = Use Result
    ATTR_IGNORE_NULLS = No
    CLIP_TO_ENVELOPE = NO
    COMBINE_GEOM = Use Result
    DATASET = $(FME_SHAREDRESOURCE_DATA)\Grondbank\Substraten\ArtikelTabel.xlsx
    FEATURETYPES = ArtikelTabel
    FORMAT = XLSXR
    INITIATOR_FIRST_OUTPUT = default
    INPUT_PORT_INITIATOR_CONNECTED = CONNECTED
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    XLSXR_ALLOW_DOLLAR_SIGNS = YES
    XLSXR_APPLY_FILTERS = No
    XLSXR_CASE_SENSITIVE_FEATURE_TYPES = YES
    XLSXR_CREATE_FEATURE_TABLES_FROM_DATA = Yes
    XLSXR_EXCEL_COL_NAMES = YES
    XLSXR_EXPANDED_DATES_SCANNING = No
    XLSXR_EXPAND_MERGED_CELLS = Yes
    XLSXR_FORCE_DATETIME = NO
    XLSXR_QUERY_FEATURE_TYPES_FOR_MERGE_FILTERS = Yes
    XLSXR_READ_BLANK_AS = Null
    XLSXR_READ_FORM_CONTROLS = NONE
    XLSXR_READ_RASTER_MODE = None
    XLSXR_REPLACE_ONLY_NEWLINES_CARRIAGE_RETURNS = YES
    XLSXR_SCAN_FOR_GEOMETRIC_TYPES = Yes
    XLSXR_SCAN_MAX_FEATURES = 1000
    XLSXR_SCHEMA_HANDLING_REVISION = 2
    XLSXR_SKIP_EMPTY_ATTRS = No
    XLSXR_SKIP_EMPTY_ROWS = YES
    XLSXR_STRIP_SHEETNAME_SPACES = YES
    XLSXR_TRIM_ATTR_NAME_WHITESPACE = Yes
    XLSXR_USE_CUSTOM_SCHEMA = NO
    ArtikelTabel -> TestFilter
FeatureReader_2
    ATTRIBUTES = Blad1,"""Project omschrijving"",Taak,Kostensoort,""Projectenkosten     organisatie"",Datum,Bomenzand,Bomenzand.formula,Bomengrond,Bomengrond.formula,Bomengranulaat,Bomengranulaat.formula,""Teelaarde plantvak"",""Teelaarde plantvak.formula"",""Teelgrond gazon"",""Teelgrond gazon.formula"",Kruidenmengsel,Kruidenmengsel.formula,""Vaste planten maaimethode"",""Vaste planten maaimethode.formula"",""Zavelgrond zeer lichte zavel"",""Zavelgrond zeer lichte zavel.formula"",""Zavelgrond matig lichte zavel"",""Zavelgrond matig lichte zavel.formula"",""Zavelgrond zware zavel"",""Zavelgrond zware zavel.formula"",""Zavelgrond lichte klei"",""Zavelgrond lichte klei.formula"",Wadisubstraat,Wadisubstraat.formula"
    ATTR_ACCUM_MODE = Only Use Result
    CLIP_TO_ENVELOPE = NO
    COMBINE_GEOM = Use Result
    DATASET = $(FME_SHAREDRESOURCE_DATA)\Grondbank\Substraten\Invulblad_afnames_landschapsubstraten_input.xlsx
    FEATURETYPES = Blad1
    FORMAT = XLSXR
    INITIATOR_FIRST_OUTPUT = default
    INPUT_PORT_INITIATOR_CONNECTED = CONNECTED
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    XLSXR_ALLOW_DOLLAR_SIGNS = YES
    XLSXR_APPLY_FILTERS = No
    XLSXR_CASE_SENSITIVE_FEATURE_TYPES = YES
    XLSXR_CONFIGURATION_DATASET = c:\temp\Grondbank\Substraten\Invulblad_afnames_landschapsubstraten_input.xlsx
    XLSXR_CREATE_FEATURE_TABLES_FROM_DATA = Yes
    XLSXR_EXCEL_COL_NAMES = YES
    XLSXR_EXPANDED_DATES_SCANNING = No
    XLSXR_EXPAND_MERGED_CELLS = Yes
    XLSXR_FORCE_DATETIME = NO
    XLSXR_QUERY_FEATURE_TYPES_FOR_MERGE_FILTERS = Yes
    XLSXR_READ_BLANK_AS = Null
    XLSXR_READ_FORM_CONTROLS = NONE
    XLSXR_READ_RASTER_MODE = None
    XLSXR_REPLACE_ONLY_NEWLINES_CARRIAGE_RETURNS = YES
    XLSXR_SCAN_FOR_GEOMETRIC_TYPES = Yes
    XLSXR_SCAN_MAX_FEATURES = 1000
    XLSXR_SCHEMA = Blad1,0,"Project omschrijving",string,,,,1,Taak,string,,,,2,Kostensoort,string,,,,3,"Projectenkosten     organisatie",string,,,,4,Datum,string,,,,5,Bomenzand,number,1,0,,5,Bomenzand.formula,string,,,,6,Bomengrond,number,1,0,,6,Bomengrond.formula,string,,,,7,Bomengranulaat,number,1,0,,7,Bomengranulaat.formula,string,,,,8,"Teelaarde plantvak",number,1,0,,8,"Teelaarde plantvak.formula",string,,,,9,"Teelgrond gazon",number,1,0,,9,"Teelgrond gazon.formula",string,,,,10,Kruidenmengsel,number,1,0,,10,Kruidenmengsel.formula,string,,,,11,"Vaste planten maaimethode",number,1,0,,11,"Vaste planten maaimethode.formula",string,,,,12,"Zavelgrond zeer lichte zavel",number,1,0,,12,"Zavelgrond zeer lichte zavel.formula",string,,,,13,"Zavelgrond matig lichte zavel",number,1,0,,13,"Zavelgrond matig lichte zavel.formula",string,,,,14,"Zavelgrond zware zavel",number,1,0,,14,"Zavelgrond zware zavel.formula",string,,,,15,"Zavelgrond lichte klei",number,1,0,,15,"Zavelgrond lichte klei.formula",string,,,,16,Wadisubstraat,number,1,0,,16,Wadisubstraat.formula,string,,,,1,,,,YES,NO,1,c:\temp\Grondbank\Substraten\Invulblad_afnames_landschapsubstraten_input.xlsx,"0,0,16,4",,NO,NO,1,2:
    XLSXR_SCHEMA_HANDLING_REVISION = 2
    XLSXR_SKIP_EMPTY_ATTRS = No
    XLSXR_SKIP_EMPTY_ROWS = YES
    XLSXR_STRIP_SHEETNAME_SPACES = YES
    XLSXR_TABLELIST = Blad1
    XLSXR_TRIM_ATTR_NAME_WHITESPACE = Yes
    XLSXR_USE_CUSTOM_SCHEMA = NO
    Blad1 -> Junction_5
Voorraad (reader XLSXR_2)
    attributes: Code char(8), Datum char(10), Status char(13), Kenteken char(8), Klant.Code number(4,0), Klant.Omschrijving char(22), Rekeningnemer.Code number(4,0), Rekeningnemer.Omschrijving char(22), Contract.Code number(11,0), Contract.Omschrijving char(50), Werklocatie.Code char(12), Werklocatie.Omschrijving char(49), Ingaand string, Artikel.Code char(7), Artikel.Omschrijving char(34), Hoeveelheid uitgaand number(6,0), Eenheid char(2), Gecorrigeerd/tegenboeking char(3), Correctie weegbon char(8)
    -> NoFeaturesTester_Bonnen
Factuur (reader XLSXR_1)
    attributes: Factuurrun.code time, Factuurrun.Omschrijving char(28), Relatie.Code number(4,0), Relatie.Omschrijving char(18), FactuurRegel.Bon.Code char(8), FactuurRegel.Bon.Datum char(10), FactuurRegel.Artikel.Code char(7), FactuurRegel.Artikel.Omschrijving char(24), FactuurRegel.Hoeveelheid number(5,2), FactuurRegel.Eenheid char(3), FactuurRegel.Correctie factuur.Code string
    -> NoFeaturesTester_Facturen

Bookmark: Krijg de juiste artikelomschrijving en maak kolommen met naam artikel en hoeveelheid.
TestFilter
    DEFAULT_VALUE = <UNFILTERED>
    PASSED_TEST_GROUP_OUTPUT = FIRST
    TEST_LIST = "BOOL_OP,OR,COMPOSITE_TEST,""""""1"""""",TEST_CLAUSE,TEST GKB_Artikel ATTRIBUTE_HAS_A_VALUE """,GKB_Artikel ATTRIBUTE_HAS_A_VALUE
    GKB_Artikel ATTRIBUTE_HAS_A_VALUE -> FeatureMerger [SUPPLIER]
FeatureMerger
    ATTR_ACCUM_MODE = Merge Supplier
    ATTR_CONFLICT_RES_LOOKUP = REQUESTOR_IF_CONFLICT
    IGNORE_NULLS = No
    JOIN_KEYS = @Trim(@Value(Artikel)) @Trim(@Value(GKB_Artikel)) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeCreator_ARTIKEL_Kolommen
    UNMERGED_REQUESTOR -> Junction_4
AttributeCreator_ARTIKEL_Kolommen
    ATTR_TABLE = SET_TO @Value(RDAM_Omschrijving) (varchar(200)) = @Value(Hoeveelheid)
    INPUT_PORT_CONNECTED = CONNECTED
    -> AttributeManager_2
    -> StatisticsCalculator
Note: Rapportage mismatched artikelen
Junction_4
    -> StatisticsCalculator_3

Bookmark: Create TOTALROW
TestFilter_formulas_aanwezig
    DEFAULT_VALUE = <UNFILTERED>
    PASSED_TEST_GROUP_OUTPUT = FIRST
    TEST_LIST:
      "BOOL_OP,OR,COMPOSITE_TEST,""""""1 OR 2 OR 3"""""",TEST_CLAUSE,TEST Bomengrond.formula ATTRIBUTE_HAS_A_VALUE ""
      TEST Bomengranulaat.formula ATTRIBUTE_HAS_A_VALUE ""
      TEST Bomenzand.formula ATTRIBUTE_HAS_A_VALUE """,TOTAL ROW
    TOTAL ROW -> AttributeManager_4
    <UNFILTERED> -> Sampler_2
AttributeManager_4
    ATTR_TABLE:
      SET_TO Project omschrijving (buffer)
      SET_TO Taak (buffer)
      SET_TO Kostensoort (buffer)
      SET_TO Projectenkosten     organisatie (buffer)
      SET_TO Datum (buffer)
      SET_TO Bomenzand (number(1,0))
      SET_TO Bomengrond (number(1,0))
      SET_TO Bomengranulaat (number(1,0))
      SET_TO Teelaarde plantvak (number(1,0))
      SET_TO Teelgrond gazon (number(1,0))
      SET_TO Kruidenmengsel (number(1,0))
      SET_TO Vaste planten maaimethode (number(1,0))
      SET_TO Zavelgrond zeer lichte zavel (number(1,0))
      SET_TO Zavelgrond matig lichte zavel (number(1,0))
      SET_TO Zavelgrond zware zavel (number(1,0))
      SET_TO Zavelgrond lichte klei (number(1,0))
      SET_TO Wadisubstraat (number(1,0))
    -> FeatureMerger_2 [REQUESTOR]
FeatureMerger_2
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> StringReplacer_ROW_in_SUM__formula
StringReplacer_ROW_in_SUM__formula
    CASE = NO
    NO_MATCH = _FME_NO_OP_
    REGEXP = YES
    STR_REPLACE_TABLE = Bomengranulaat.formula,Bomengrond.formula,Bomenzand.formula,Kruidenmengsel.formula,Teelaarde plantvak.formula,Teelgrond gazon.formula,Vaste planten maaimethode.formula,Wadisubstraat.formula,Zavelgrond lichte klei.formula,Zavelgrond matig lichte zavel.formula,Zavelgrond zeer lichte zavel.formula,Zavelgrond zware zavel.formula \d{1,5}\) @sum(@Value(_rapportageregels),2))
    -> ExcelStyler_2
ExcelStyler_2
    CELL_BORDER_COLOR = 0.647059,0.647059,0.647059
    CELL_BORDER_STYLE = BORDERSTYLE_THIN
    FONT_COLOR = 0,0,0
    FONT_NAME = Calibri,11,BOLD
    HORIZONTAL_ALIGNMENT = center
    PATTERN_COLOR = 0.929412,0.929412,0.929412
    PATTERN_STYLE = FILLPATTERN_SOLID
    ROW_HEIGHT = 13.30
    ROW_OR_CELL = row
    TEXT_ORIENTATION = 0
    VERTICAL_ALIGNMENT = top
    ExcelStyled -> Counter__row_2
Counter__row_2
    CNT_ATTR = _row
    SCOPE = Local
    START = 1000
    -> Sorter_op__row_2

Bookmark: Create tussenregel voor een dubbele lijn boven de totalrow
Sampler_2
    MODE = ORIGINAL
    RATE = 1
    SAMPLE_TYPE_MULTIPLIER = -1
    SAMPLE_MODE = No
    SAMPLE_TYPE_LONG = First N Features
    SAMPLED -> AttributeManager_5
AttributeManager_5
    ATTR_TABLE:
      SET_TO Bomengranulaat.formula (buffer)
      SET_TO Bomengrond.formula (buffer)
      SET_TO Bomenzand.formula (buffer)
      SET_TO Kruidenmengsel.formula (buffer)
      SET_TO Teelaarde plantvak.formula (buffer)
      SET_TO Teelgrond gazon.formula (buffer)
      SET_TO Vaste planten maaimethode.formula (buffer)
      SET_TO Wadisubstraat.formula (buffer)
      SET_TO Zavelgrond lichte klei.formula (buffer)
      SET_TO Zavelgrond matig lichte zavel.formula (buffer)
      SET_TO Zavelgrond zeer lichte zavel.formula (buffer)
      SET_TO Zavelgrond zware zavel.formula (buffer)
      SET_TO Project omschrijving (buffer)
      SET_TO Taak (buffer)
      SET_TO Kostensoort (buffer)
      SET_TO Projectenkosten     organisatie (buffer)
      SET_TO Datum (buffer)
      SET_TO Bomenzand (number(1,0))
      SET_TO Bomengrond (number(1,0))
      SET_TO Bomengranulaat (number(1,0))
      SET_TO Teelaarde plantvak (number(1,0))
      SET_TO Teelgrond gazon (number(1,0))
      SET_TO Kruidenmengsel (number(1,0))
      SET_TO Vaste planten maaimethode (number(1,0))
      SET_TO Zavelgrond zeer lichte zavel (number(1,0))
      SET_TO Zavelgrond matig lichte zavel (number(1,0))
      SET_TO Zavelgrond zware zavel (number(1,0))
      SET_TO Zavelgrond lichte klei (number(1,0))
      SET_TO Wadisubstraat (number(1,0))
    -> ExcelStyler_3
ExcelStyler_3
    CELL_BORDER_COLOR = 0.647059,0.647059,0.647059
    CELL_BORDER_STYLE = BORDERSTYLE_THIN
    FONT_COLOR = 0,0,0
    FONT_NAME = Calibri,11,BOLD
    HORIZONTAL_ALIGNMENT = center
    PATTERN_COLOR = 0.929412,0.929412,0.929412
    PATTERN_STYLE = FILLPATTERN_SOLID
    ROW_HEIGHT = 15
    ROW_OR_CELL = row
    TEXT_ORIENTATION = 0
    VERTICAL_ALIGNMENT = top
    ExcelStyled -> Counter__row_3
Counter__row_3
    CNT_ATTR = _row
    SCOPE = Local
    START = 500
    -> Sorter_op__row_2

Bookmark: Rapportage
AttributeCreator_LOGMESSAGE_Geen_bonnen_gelezen_log_volgorde_2
    ATTR_TABLE:
      SET_TO LogMessage (varchar(77)) = <font color=red>Bonnenbestand;Er zijn geen bonregels ingelezen !!!</font><br>
      SET_TO log_volgorde (uint8) = 2
    INPUT_PORT_CONNECTED = CONNECTED
    -> Sorter_log_volgorde
AttributeCreator_LOGMESSAGE_Geen_bonnen_gelezen_log_volgorde_1
    ATTR_TABLE:
      SET_TO LogMessage (varchar(83)) = <font color=red>Facturenbestand;Er zijn geen factuurregels ingelezen !!!</font><br>
      SET_TO log_volgorde (uint8) = 1
    INPUT_PORT_CONNECTED = CONNECTED
    -> Sorter_log_volgorde
StatisticsCalculator_2
    ATTR_ACCUM_MODE = None
    CALCULATION_MODE = NUMERIC
    FEAT_STATS = Relatie.Code,NUMERIC_MODE,,,COUNT,,,,,,,,,,
    SUMMARY -> AttributeCreator_LOGMESSAGE_Totalen_log_volgorde_0.5
AttributeCreator_LOGMESSAGE_Totalen_log_volgorde_0.5
    ATTR_TABLE:
      SET_TO LogMessage (varchar(200)) = Totalen; <strong> <font color=red>@Value(Relatie.Code.total_count) </strong> factuurregels van andere relaties ! Deze worden niet verwerkt. </font><br>
      SET_TO log_volgorde (real32) = 0.5
    INPUT_PORT_CONNECTED = CONNECTED
    -> Sorter_log_volgorde
StatisticsCalculator
    ATTR_ACCUM_MODE = None
    CALCULATION_MODE = NUMERIC
    FEAT_STATS = FactuurRegel.Hoeveelheid,NUMERIC_MODE,,,,SUM,,,,,,,,,;FactuurRegel.Artikel.Code,NUMERIC_MODE,,,COUNT,,,,,,,,,,;FactuurRegel.Artikel.Omschrijving.total_count,NUMERIC_MODE,,,,SUM,,,,,,,,,
    GROUP_BY = _totaal_aantal_bonnen _totaal_aantal_factuurregels Artikel RDAM_Omschrijving _aantal_factuurregels_RDAM _result_datetime
    SUMMARY -> Aggregator
    SUMMARY -> AttributeRounder
Aggregator
    ACCUM_ATTRS = One
    MODE = Attributes Only
    SEP = ,
    SUM = FactuurRegel.Artikel.Code.total_count FactuurRegel.Hoeveelheid.sum
    AGGREGATE -> AttributeCreator_LOGMESSAGE_Totalen_RDAM_log_volgorde_0
AttributeCreator_LOGMESSAGE_Totalen_RDAM_log_volgorde_0
    ATTR_TABLE:
      SET_TO LogMessage (varchar(200)) = Totalen; <strong> <font color=darkgreen>@Value(_aantal_factuurregels_RDAM)</font> </strong> factuurregels voor RDAM <br>
        Totalen; <strong> <font color=darkgreen>@Value(_totaal_aantal_factuurregels)</font> </strong> factuurregels, <strong> <font color=darkgreen>@Value(_totaal_aantal_bonnen)</font> </strong> bonregels.<br>

      SET_TO log_volgorde (uint8) = 0
    INPUT_PORT_CONNECTED = CONNECTED
    -> Sorter_log_volgorde
AttributeRounder
    PLACES = 2
    ROUND_TYPE_TCL = round
    SRC_ATTRS = FactuurRegel.Artikel.Code.total_count FactuurRegel.Hoeveelheid.sum
    ROUND_TYPE = Nearest
    -> HTMLReportGenerator_2
HTMLReportGenerator_2
    CONTENT_LIST = TABLE
    PAGE_CONFIG = TABLE{{STYLE;DEFAULT;TABLE;Artikel|Artikel/RDAM_Omschrijving|RDAM Artikel/FactuurRegel.Hoeveelheid.sum|Hoeveelheid/FactuurRegel.Artikel.Omschrijving.total_count.sum|Aantal bonnen;FME_CONTROLLER_QUERY_FILE;transformers/dependencies/html5/Table.fme;FME_CONTROLLER_CHOICE;Table}}
    -> AttributeCreator_html_volgorde_2
AttributeCreator_html_volgorde_2
    ATTR_TABLE = SET_TO html_volgorde (uint8) = 3
    INPUT_PORT_CONNECTED = CONNECTED
    -> StringReplacer_2
StringReplacer_2
    CASE = NO
    NO_MATCH = _FME_NO_OP_
    REGEXP = NO
    STR_REPLACE_TABLE = html_content  <body> <div style="text-align:center;color:darkgreen">Overzicht verwerkte artikelen in overzicht</div> <body>
    -> Sorter_html_volgorde
StatisticsCalculator_3
    ATTR_ACCUM_MODE = None
    CALCULATION_MODE = NUMERIC
    FEAT_STATS = Code,NUMERIC_MODE,,,COUNT,,,,,,,,,,;Hoeveelheid,NUMERIC_MODE,,,,SUM,,,,,,,,,
    GROUP_BY = Artikel
    SUMMARY -> AttributeRounder_2
AttributeRounder_2
    PLACES = 2
    ROUND_TYPE_TCL = round
    SRC_ATTRS = Hoeveelheid.sum
    ROUND_TYPE = Nearest
    -> HTMLReportGenerator_4
HTMLReportGenerator_4
    CONTENT_LIST = TABLE
    PAGE_CONFIG = TABLE{{STYLE;DEFAULT;TABLE;Artikel|Onbekende artikelen/Code.total_count|Aantal bonnen/Hoeveelheid.sum|Hoeveelheid;FME_CONTROLLER_QUERY_FILE;transformers/dependencies/html5/Table.fme;FME_CONTROLLER_CHOICE;Table}}
    -> AttributeCreator_html_volgorde_4
AttributeCreator_html_volgorde_4
    ATTR_TABLE = SET_TO html_volgorde (uint8) = 2
    INPUT_PORT_CONNECTED = CONNECTED
    -> StringReplacer
StringReplacer
    CASE = NO
    NO_MATCH = _FME_NO_OP_
    REGEXP = NO
    STR_REPLACE_TABLE = html_content  <body> <div style="text-align:center;color:red"><mark>Er zijn onbekende artikelen aangetroffen. <br>Deze worden niet meegenomen in de facturatie.</mark><br>Zie overzicht hieronder.</div> <body>
    -> Sorter_html_volgorde
FeatureCounter_3
    FeatureCounterNewAttrParameter = _numfeatures
    GroupBox = NO
    -> AttributeExposer_3
AttributeExposer_3
    ATTR_TABLE = _numfeatures,int32
    -> Sampler_3
Sampler_3
    MODE = ORIGINAL
    RATE = 1
    SAMPLE_TYPE_MULTIPLIER = -1
    SAMPLE_MODE = No
    SAMPLE_TYPE_LONG = First N Features
    SAMPLED -> AttributeCreator_LOGMESSAGE_Factuur-Bon_bestand_incompleet_log_volgorde_3
AttributeCreator_LOGMESSAGE_Factuur-Bon_bestand_incompleet_log_volgorde_3
    ATTR_TABLE:
      SET_TO LogMessage (varchar(200)) = <font color=red>@Value(fme_feature_type);Het geselecteerde bestand bevat niet alle benodigde velden of de velden zijn niet gevuld. <br><br>Totaal <strong> @Value(_numfeatures) </strong> incomplete regels !!!</font><br>
      SET_TO log_volgorde (uint8) = 3
    INPUT_PORT_CONNECTED = CONNECTED
    -> Sorter_log_volgorde
AttributeCreator_LOGMESSAGE_Ontbrekende_bonnen_log_volgorde_4
    ATTR_TABLE:
      SET_TO LogMessage (varchar(200)) = <strong><font color=red>Bonnen; Bonbestand @Value(FactuurRegel.Bon.Code) ontbreekt bij de facturen !</font><br></strong>
      SET_TO log_volgorde (uint8) = 4
    INPUT_PORT_CONNECTED = CONNECTED
    -> Sorter_log_volgorde
Sorter_log_volgorde
    SORT_PARM = log_volgorde NATURAL ASCENDING NON_VALUES_BEFORE_VALUES
    SORTED -> AttributeCombiner
AttributeCombiner
    ATTRS = LogMessage
    DELIM = <br>
    DROP_EMPTY = No
    QUOT = None
    -> FilenamePartExtractor_factuurbestand
FilenamePartExtractor_factuurbestand
    FULLNAME_ATTR = _factuurbestand
    SRC_ATTR = $(Factuur_XLSX)
    -> FilenamePartExtractor_bonbestand
FilenamePartExtractor_bonbestand
    FULLNAME_ATTR = _bonnenbestand
    SRC_ATTR = $(Bonnen_XLSX)
    -> Junction_2
Junction_2
    -> HTMLReportGenerator
    -> HTMLReportGenerator_3
HTMLReportGenerator
    CONTENT_LIST = HEADER SEPARATOR HEADER SEPARATOR HTML SEPARATOR HTML
    PAGE_CONFIG:
      HEADER{{TEXT;Invulstaat landschapsubstraten;HEADER;H3;HEADER_ID;;ALIGNMENT;CENTER;COLOR;0,0,0;FME_CONTROLLER_QUERY_FILE;transformers/dependencies/html5/Header.fme;FME_CONTROLLER_CHOICE;Header}}SEPARATOR{{WIDTH;1;FME_CONTROLLER_QUERY_FILE;transformers/dependencies/html5/Separator.fme;FME_CONTROLLER_CHOICE;Separator}}HEADER{{TEXT;d.d. @DateTimeFormat(@Value(_result_datetime),%d-%m-%Y %H:%M);HEADER;H6;HEADER_ID;;ALIGNMENT;CENTER;COLOR;0,0,0;FME_CONTROLLER_QUERY_FILE;transformers/dependencies/html5/Header.fme;FME_CONTROLLER_CHOICE;Header}}SEPARATOR{{WIDTH;1;FME_CONTROLLER_QUERY_FILE;transformers/dependencies/html5/Separator.fme;FME_CONTROLLER_CHOICE;Separator}}HTML{{HTML;<div style="text-align:center">Gebruikte bestanden:
      <br/>
      Factuurbestand: <strong><font color=darkgreen>@Value(_factuurbestand)</font></strong><br>
      <p>Bonnenbestand: <strong><font color=darkgreen>@Value(_bonnenbestand)</font></strong><br> </p>

      </div>;FME_CONTROLLER_QUERY_FILE;transformers/dependencies/html5/Custom HTML.fme;FME_CONTROLLER_CHOICE;Custom HTML}}SEPARATOR{{WIDTH;1;FME_CONTROLLER_QUERY_FILE;transformers/dependencies/html5/Separator.fme;FME_CONTROLLER_CHOICE;Separator}}HTML{{HTML;<div style="text-align:center">Log:<br>@Value(LogMessage)<br><br></div>;FME_CONTROLLER_QUERY_FILE;transformers/dependencies/html5/Custom HTML.fme;FME_CONTROLLER_CHOICE;Custom HTML}}
    -> AttributeCreator_html_volgorde_1
AttributeCreator_html_volgorde_1
    ATTR_TABLE = SET_TO html_volgorde (uint8) = 1
    INPUT_PORT_CONNECTED = CONNECTED
    -> Sorter_html_volgorde
HTMLReportGenerator_3
    CONTENT_LIST = SEPARATOR HTML
    PAGE_CONFIG = SEPARATOR{{WIDTH;1;FME_CONTROLLER_QUERY_FILE;transformers/dependencies/html5/Separator.fme;FME_CONTROLLER_CHOICE;Separator}}HTML{{HTML;<div style="text-align:center">Mail verstuurd aan <strong> $(EMAILADRES)</strong>.</div>;FME_CONTROLLER_QUERY_FILE;transformers/dependencies/html5/Custom HTML.fme;FME_CONTROLLER_CHOICE;Custom HTML}}
    -> AttributeCreator_html_volgorde_3
AttributeCreator_html_volgorde_3
    ATTR_TABLE = SET_TO html_volgorde (uint8) = 4
    INPUT_PORT_CONNECTED = CONNECTED
    -> Sorter_html_volgorde
Sorter_html_volgorde
    SORT_PARM = html_volgorde NATURAL ASCENDING NON_VALUES_BEFORE_VALUES
    SORTED -> FeatureWriter_LOG_HTML [HTML]
FeatureWriter_LOG_HTML
    CONFIG_PARAMETERS = ESCAPE_COMMAS_IN_FTP_FORMAT_PARAMETERS,no
    DATASET = log.html
    DATASET_ATTR = _dataset
    FEATURE_TYPE_LIST_ATTR = _feature_types
    FORMAT = HTML
    HTML_COORDINATE_SYSTEM_GRANULARITY = FEATURE
    HTML_DESTINATION_DATASETTYPE_VALIDATION = Yes
    HTML_ENCODING = UTF8
    HTML_END_OF_LINE = System
    HTML_MIME_TYPE = text/html
    HTML_OVERWRITE_FILE = YES
    HTML_WRITE_LAST_EOL = YES
    HTML_WRITE_UTF8_BOM = YES
    TOTAL_FEATURES_WRITTEN_ATTR = _total_features_written
    SUMMARY -> FeatureMerger_4 [REQUESTOR]

Bookmark: CHECK DATA
FeatureCounter
    FeatureCounterNewAttrParameter = _totaal_aantal_bonnen
    GroupBox = NO
    -> AttributeExposer
AttributeExposer
    ATTR_TABLE = _totaal_aantal_bonnen,int32
    -> TestFilter_BON_KENMERKEN
TestFilter_BON_KENMERKEN
    DEFAULT_VALUE = Bonbestand incompleet
    PASSED_TEST_GROUP_OUTPUT = FIRST
    TEST_LIST:
      "BOOL_OP,COMPOSITE,COMPOSITE_TEST,""""""NOT ( 1 OR 2 OR 3 OR 4 ) AND ( 5 AND 6 AND 7 AND 8 )"""""",TEST_CLAUSE,TEST Code ATTRIBUTE_IS_MISSING ""
      TEST Contract.Omschrijving ATTRIBUTE_IS_MISSING ""
      TEST Werklocatie.Code ATTRIBUTE_IS_MISSING ""
      TEST Werklocatie.Omschrijving ATTRIBUTE_IS_MISSING ""
      TEST Code ATTRIBUTE_HAS_A_VALUE ""
      TEST Contract.Omschrijving ATTRIBUTE_HAS_A_VALUE ""
      TEST Werklocatie.Code ATTRIBUTE_HAS_A_VALUE ""
      TEST Werklocatie.Omschrijving ATTRIBUTE_HAS_A_VALUE """,Alle velden in bonbestand aanwezig
    Alle velden in bonbestand aanwezig -> AttributeKeeper_Code_en_ContractOmschrijving
    Bonbestand incompleet -> Junction_3
FeatureCounter_2
    FeatureCounterNewAttrParameter = _totaal_aantal_factuurregels
    GroupBox = NO
    -> AttributeExposer_2
AttributeExposer_2
    ATTR_TABLE = _totaal_aantal_factuurregels,int32
    -> TestFilter_relatiecode_1136_1139
TestFilter_relatiecode_1136_1139
    DEFAULT_VALUE = Overige relaties
    PASSED_TEST_GROUP_OUTPUT = FIRST
    TEST_LIST = "BOOL_OP,OR,COMPOSITE_TEST,""""""1"""""",TEST_CLAUSE,NUM_TEST @Value(Relatie.Code) IN 1136,1139",Relatiecode 1136,1139 = Rotterdam
    Relatiecode 1136,1139 = Rotterdam -> TestFilter_FAKTUUR_KENMERKEN
    Overige relaties -> StatisticsCalculator_2
TestFilter_FAKTUUR_KENMERKEN
    DEFAULT_VALUE = Factuurbestand incompleet
    PASSED_TEST_GROUP_OUTPUT = FIRST
    TEST_LIST:
      "BOOL_OP,COMPOSITE,COMPOSITE_TEST,""""""NOT ( 1 OR 2 OR 3 OR 4 ) AND ( 5 AND 6 AND 7 AND 8 )"""""",TEST_CLAUSE,TEST FactuurRegel.Bon.Code ATTRIBUTE_IS_MISSING ""
      TEST FactuurRegel.Artikel.Omschrijving ATTRIBUTE_IS_MISSING ""
      TEST FactuurRegel.Bon.Datum ATTRIBUTE_IS_MISSING ""
      TEST FactuurRegel.Hoeveelheid ATTRIBUTE_IS_MISSING ""
      TEST FactuurRegel.Bon.Code ATTRIBUTE_HAS_A_VALUE ""
      TEST FactuurRegel.Artikel.Omschrijving ATTRIBUTE_HAS_A_VALUE ""
      TEST FactuurRegel.Bon.Datum ATTRIBUTE_HAS_A_VALUE ""
      TEST FactuurRegel.Hoeveelheid ATTRIBUTE_HAS_A_VALUE """,Alle velden in factuurbestand aanwezig
    Alle velden in factuurbestand aanwezig -> FeatureMerger_ContractOmschrijving_aan_Factuur [SUPPLIER]
    Alle velden in factuurbestand aanwezig -> UniqueValueLogger
    Factuurbestand incompleet -> Junction_3
Note: Rapportage
Junction_3
    -> FeatureCounter_3

Bookmark: Koppel benodigde velden van voorraad(bonnen) aan de factuur
AttributeKeeper_Code_en_ContractOmschrijving
    CREATE_BULK_MODE_FEATURES = NO
    KEEP_ATTRS = Code,Contract.Omschrijving,_totaal_aantal_bonnen,Werklocatie.Code,Werklocatie.Omschrijving
    -> FeatureMerger_ContractOmschrijving_aan_Factuur [REQUESTOR]
FeatureMerger_ContractOmschrijving_aan_Factuur
    ATTR_ACCUM_MODE = Merge Supplier
    ATTR_CONFLICT_RES_LOOKUP = REQUESTOR_IF_CONFLICT
    IGNORE_NULLS = No
    JOIN_KEYS = @Value(Code) @Value(FactuurRegel.Bon.Code) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeExposer_invulblad
    <REJECTED> -> FeatureMerger_ContractOmschrijving_aan_Factuur__Rejected_

Bookmark: Add attributes from template
AttributeExposer_invulblad
    ATTR_TABLE = _rows,int32,"Projectenkosten     organisatie",buffer,Bomengranulaat,buffer,Bomengrond,buffer,Bomenzand,buffer,Kruidenmengsel,buffer,"Teelaarde plantvak",buffer,"Teelgrond gazon",buffer,"Vaste planten maaimethode",buffer,Wadisubstraat,buffer,"Zavelgrond lichte klei",buffer,"Zavelgrond matig lichte zavel",buffer,"Zavelgrond zeer lichte zavel",buffer,"Zavelgrond zware zavel",buffer
    -> AttributeManager_3
AttributeManager_3
    ATTR_TABLE:
      RENAME_SET_VALUE FactuurRegel.Bon.Datum > Datum (varchar(10))
      SET_TO Projectenkosten     organisatie (buffer) = ""
      SET_TO Bomengranulaat (buffer) = 0
      SET_TO Bomengrond (buffer) = 0
      SET_TO Bomenzand (buffer) = 0
      SET_TO Kruidenmengsel (buffer) = 0
      SET_TO Teelaarde plantvak (buffer) = 0
      SET_TO Teelgrond gazon (buffer) = 0
      SET_TO Vaste planten maaimethode (buffer) = 0
      SET_TO Wadisubstraat (buffer) = 0
      SET_TO Zavelgrond lichte klei (buffer) = 0
      SET_TO Zavelgrond matig lichte zavel (buffer) = 0
      SET_TO Zavelgrond zeer lichte zavel (buffer) = 0
      SET_TO Zavelgrond zware zavel (buffer) = 0
    -> AttributeSplitter_op__

Bookmark: ContractOmschrijving opslitsen in onderdelen
AttributeSplitter_op__
    ATTR_NAME = Contract.Omschrijving
    DELIMITER = #
    DROP_EMPTY_PARTS = NO
    LIST_NAME = _contract
    TRIM_TYPE = BOTH
    -> AttributeCreator_ProjectOmschrijving_Taak_en_Kostensoort
AttributeCreator_ProjectOmschrijving_Taak_en_Kostensoort
    ATTR_TABLE:
      SET_TO Project omschrijving (varchar(200)) = @Value(Werklocatie.Code) <pipe> @Value(Werklocatie.Omschrijving)
      SET_TO Taak (varchar(200)) = @Value(_contract{1})
      SET_TO Kostensoort (varchar(200)) = @Value(_contract{2})
    INPUT_PORT_CONNECTED = CONNECTED
    -> FeatureCounter_4

Bookmark: Groepeer en sum hoeveelheid per ......
FeatureCounter_4
    FeatureCounterNewAttrParameter = _aantal_factuurregels_RDAM
    GroupBox = NO
    -> AttributeExposer_4
AttributeExposer_4
    ATTR_TABLE = _aantal_factuurregels_RDAM,
    -> StatisticsCalculator_HVH_per_rapportageregel
StatisticsCalculator_HVH_per_rapportageregel
    ATTR_ACCUM_MODE = One
    CALCULATION_MODE = NUMERIC
    FEAT_STATS = FactuurRegel.Hoeveelheid,NUMERIC_MODE,,,,SUM,,,,,,,,,;FactuurRegel.Artikel.Omschrijving,NUMERIC_MODE,,,COUNT,,,,,,,,,,
    GROUP_BY = "Project omschrijving" Taak Kostensoort Datum FactuurRegel.Artikel.Omschrijving _aantal_factuurregels_RDAM
    SUMMARY -> AttributeManager
AttributeManager
    ATTR_TABLE:
      RENAME_SET_VALUE FactuurRegel.Artikel.Omschrijving > Artikel (varchar(24))
      RENAME_SET_VALUE FactuurRegel.Hoeveelheid.sum > Hoeveelheid (real64)
    USER_EXPOSED_ATTRIBUTES = Project omschrijving,Taak,Kostensoort,Artikel,FactuurRegel.Bon.Datum,Code,Contract.Omschrijving,Factuurrun.code,Factuurrun.Omschrijving,Relatie.Code,Relatie.Omschrijving,FactuurRegel.Bon.Code,FactuurRegel.Artikel.Code,FactuurRegel.Artikel.Omschrijving,FactuurRegel.Hoeveelheid,FactuurRegel.Eenheid,FactuurRegel.Correctie factuur.Code,_artikel{},_element_count,_contract{},FactuurRegel.Hoeveelheid.sum,Artikel.total_count,Projectenkosten     organisatie,Datum,Bomengranulaat,Bomengrond,Bomenzand,Kruidenmengsel,Teelaarde plantvak,Teelgrond gazon,Vaste planten maaimethode,Wadisubstraat,Zavelgrond lichte klei,Zavelgrond matig lichte zavel,Zavelgrond zeer lichte zavel,Zavelgrond zware zavel,_rows,FactuurRegel.Artikel.Omschrijving.total_count
    -> FeatureMerger [REQUESTOR]

Bookmark: Haal schema op uit XLSX, koppel deze en schrijf het output bestand
AttributeManager_2
    ATTR_TABLE:
      SET_TO Projectenkosten     organisatie (buffer)
      REMOVE Hoeveelheid (real64)
      REMOVE FactuurRegel.Artikel.Omschrijving.total_count (uint64)
      REMOVE GKB_Artikel (varchar(24))
      REMOVE RDAM_Omschrijving (varchar(29))
      REMOVE Artikel (varchar(24))
      REMOVE Code (varchar(8))
      REMOVE Contract.Omschrijving (varchar(50))
      REMOVE Factuurrun.code (time)
      REMOVE Factuurrun.Omschrijving (varchar(28))
      REMOVE Relatie.Code (number(4,0))
      REMOVE Relatie.Omschrijving (varchar(18))
      REMOVE FactuurRegel.Bon.Code (varchar(8))
      REMOVE FactuurRegel.Artikel.Code (varchar(7))
      REMOVE FactuurRegel.Hoeveelheid (number(5,2))
      REMOVE FactuurRegel.Eenheid (varchar(3))
      REMOVE FactuurRegel.Correctie factuur.Code (buffer)
      REMOVE _contract{} (varchar(200))
    -> FeatureCounter_productrijen
FeatureCounter_productrijen
    FeatureCounterNewAttrParameter = _rapportageregels
    GroupBox = NO
    -> AttributeExposer_2_productrijen
AttributeExposer_2_productrijen
    ATTR_TABLE = _rapportageregels,
    -> ExcelStyler
    -> Sampler
ExcelStyler
    BACKGROUND_COLOR = 0.929412,0.929412,0.929412
    CELL_BORDER_COLOR = 0.647059,0.647059,0.647059
    CELL_BORDER_STYLE = BORDERSTYLE_THIN
    FONT_NAME = Calibri,11
    HORIZONTAL_ALIGNMENT = left
    PATTERN_COLOR = 0.929412,0.929412,0.929412
    PATTERN_STYLE = FILLPATTERN_SOLID
    ROW_HEIGHT = 13.30
    ROW_OR_CELL = row
    TEXT_ORIENTATION = 0
    VERTICAL_ALIGNMENT = top
    ExcelStyled -> ExcelStyler_4
ExcelStyler_4
    ATTRS_TO_STYLE = Bomengranulaat Bomengrond Bomenzand Kruidenmengsel "Teelaarde plantvak" "Teelgrond gazon" "Vaste planten maaimethode" Wadisubstraat "Zavelgrond lichte klei" "Zavelgrond matig lichte zavel" "Zavelgrond zeer lichte zavel" "Zavelgrond zware zavel"
    BACKGROUND_COLOR = 0.929412,0.929412,0.929412
    CELL_BORDER_COLOR = 0.647059,0.647059,0.647059
    CELL_BORDER_STYLE = BORDERSTYLE_THIN
    FONT_NAME = Calibri,11
    HORIZONTAL_ALIGNMENT = center
    PATTERN_COLOR = 0.929412,0.929412,0.929412
    PATTERN_STYLE = FILLPATTERN_SOLID
    ROW_OR_CELL = cell
    TEXT_ORIENTATION = 0
    VERTICAL_ALIGNMENT = top
    ExcelStyled -> Counter__row
Counter__row
    CNT_ATTR = _row
    SCOPE = Local
    START = 1
    -> Sorter_op__row
Sorter_op__row_2
    SORT_PARM = _row NUMERIC DESCENDING NON_VALUES_AFTER_VALUES
    SORTED -> Sorter_op__row
Sorter_op__row
    SORT_PARM = _row NUMERIC ASCENDING NON_VALUES_BEFORE_VALUES
    SORTED -> AttributeManager_6
AttributeManager_6
    ATTR_TABLE:
      SET_TO ExcelDoelbestand (varchar(200)) = FME_CONDITIONAL:DEFAULT_VALUE'_FME_NO_OP_'BOOL_OP;OR;COMPOSITE_TEST;1;TEST ExcelDoelbestand ATTRIBUTE_IS_MISSING _FME_BLANK_STRING_'@Value(feature[-1].ExcelDoelbestand)'FME_NUM_CONDITIONS2___
      SET_TO ExcelDoelPath (varchar(200)) = FME_CONDITIONAL:DEFAULT_VALUE'_FME_NO_OP_'BOOL_OP;OR;COMPOSITE_TEST;1;TEST ExcelDoelPath ATTRIBUTE_IS_MISSING _FME_BLANK_STRING_'@Value(feature[-1].ExcelDoelPath)'FME_NUM_CONDITIONS2___
    NUM_PRIOR_FEATURES = 1
    NUM_SUBSEQUENT_FEATURES = 1
    -> AttributeRemover
AttributeRemover
    REMOVE_ATTRS = _row,_rows,_rapportageregels
    -> FeatureWriter_Excel [Merged]
FeatureWriter_Excel
    CONFIG_PARAMETERS = ESCAPE_COMMAS_IN_FTP_FORMAT_PARAMETERS,no
    DATASET = @Value(ExcelDoelPath)
    DATASET_ATTR = _dataset
    FEATURE_TYPE_LIST_ATTR = _feature_types
    FORMAT = XLSXW
    MORE_SUMMARY_ATTRS = Datum DatumStamp ExcelDoelPath ExcelDoelbestand DoelPath
    TOTAL_FEATURES_WRITTEN_ATTR = _total_features_written
    XLSXW_ALWAYS_CREATE_FEATURE_TYPES = YES
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_OUT = No
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TEMPLATEFILE = $(FME_SHAREDRESOURCE_DATA)\Grondbank\Substraten\Invulblad_afnames_landschapsubstraten.xlsx
    XLSXW_TEMPLATE_SHEET = Blad1
    XLSXW_TRUNCATE_TABLE = No
    XLSXW_WRITER_MODE = Insert
    SUMMARY -> Junction_6
    SUMMARY -> GKB_EmailGenerator
Junction_6
    -> FeatureMerger_5 [SUPPLIER]
FeatureMerger_5
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> FeatureMerger_4 [SUPPLIER]
GKB_EmailGenerator
    ATTACHMENT = @Value(_dataset)
    Body = Goedendag,<br><br><br>Hierbij ontvangt u het 2-wekeljkse overzicht van de afnames landschapsubstraten overeenkomstig contract 1-L-20214-24. d.d. @DateTimeFormat(@DateTimeNow(),%Y%m%d) (week @DateTimeFormat(@DateTimeNow(),%U)) <br><br><br> Met vriendelijke groet, <br><br>Grondbank IJsselmonde bv <br><br><br><br><small>Dit bericht is automatisch aangemaakt en daarom niet ondertekend.</small>
    Subject = GKB Invulblad afnames landschapsubstraten @Value(_feature_types{0}.DatumStamp)
    To = $(EMAILADRES)
    VERZAMEL_MAIL = YES
GKB_EmailGenerator_2 [off]
    Body = Goedendag,<br><br><br>Hierbij ontvangt u het 2-wekeljkse overzicht van de afnames landschapsubstraten overeenkomstig contract 1-L-20214-24. d.d. @DateTimeFormat(@DateTimeNow(),%Y%m%d) (week @DateTimeFormat(@DateTimeNow(),%U)) <br><br><br> Met vriendelijke groet, <br><br>Grondbank IJsselmonde bv <br><br><br><br><small>Dit bericht is automatisch aangemaakt en daarom niet ondertekend.</small>
    Subject = GKB Invulblad afnames landschapsubstraten @Value(_feature_types{0}.DatumStamp)
    To = $(EMAILADRES)
    VERZAMEL_MAIL = YES

Bookmark: Aantal rapportage regels doorgeven
Sampler
    MODE = ORIGINAL
    RATE = 1
    SAMPLE_TYPE_MULTIPLIER = -1
    SAMPLE_MODE = No
    SAMPLE_TYPE_LONG = First N Features
    SAMPLED -> AttributeKeeper
AttributeKeeper
    CREATE_BULK_MODE_FEATURES = NO
    KEEP_ATTRS = _rapportageregels,ExcelDoelPath,ExcelDoelbestand
    -> FeatureMerger_2 [SUPPLIER]

Bookmark: PDF bonnen ophalen en verpakken
AzureFileStorageConnector_List
    ACCOUNT_NAME = fmegrondbank
    CREDENTIAL_SOURCE = SAS
    INPUT_PORT_CONNECTED = CONNECTED
    OPERATION_TYPE = List
    PARAMETER_SETUP = _FME_AZURE_CONTAINER_List][{"display":"fme","value":"fme"}]]_FME_FILES_List][{"display":"/PB_Rotterdam","value":"PB_Rotterdam"}]]_FME_INCLUDE_SUBFOLDERS_List]Yes]_FME_ATTRIBUTES_TO_ADD_List]_url _full_path _name _file_or_folder _file_size _relative_path _created _last_modified]_FME_ATTRIBUTES_TO_ADD]_url _full_path _name _file_or_folder _file_size _relative_path _created _last_modified]_FME_AZURE_CONTAINER][{"display":"fme","value":"fme"}]]_FME_FILES][{"display":"/PB_Rotterdam","value":"PB_Rotterdam"}]]_FME_INCLUDE_SUBFOLDERS]Yes
    _FME_ATTRIBUTES_TO_ADD = _url _full_path _name _file_or_folder _file_size _relative_path _created _last_modified
    _FME_ATTRIBUTES_TO_ADD_List = _url _full_path _name _file_or_folder _file_size _relative_path _created _last_modified
    _FME_AZURE_CONTAINER = [{"display":"fme","value":"fme"}]
    _FME_AZURE_CONTAINER_List = [{"display":"fme","value":"fme"}]
    _FME_AZURE_SAS_TOKEN = $(SAS_fmegrondbank)
    _FME_FILES = [{"display":"/PB_Rotterdam","value":"PB_Rotterdam"}]
    _FME_FILES_List = [{"display":"/PB_Rotterdam","value":"PB_Rotterdam"}]
    _FME_INCLUDE_SUBFOLDERS = Yes
    _FME_INCLUDE_SUBFOLDERS_List = Yes
    -> TestFilter_Folders_Files
TestFilter_Folders_Files
    DEFAULT_VALUE = Folders en andere bestanden
    PASSED_TEST_GROUP_OUTPUT = FIRST
    TEST_LIST:
      "BOOL_OP,AND,COMPOSITE_TEST,""""""1 AND 2"""""",TEST_CLAUSE,TEST @Value(_file_or_folder) = File
      CASE_INSENSITIVE_TEST @Value(_name) CONTAINS pdf",PDF Bestanden
    PDF Bestanden -> FilenamePartExtractor
FilenamePartExtractor
    EXTENSION_ATTR = _extension
    ROOTNAME_ATTR = _rootname
    SRC_ATTR = @Value(_name)
    -> FeatureMerger_3 [REQUESTOR]
FeatureMerger_3
    ATTR_ACCUM_MODE = Merge Supplier
    ATTR_CONFLICT_RES_LOOKUP = REQUESTOR_IF_CONFLICT
    IGNORE_NULLS = No
    JOIN_KEYS = @Value(_rootname) @Value(FactuurRegel.Bon.Code) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AzureFileStorageConnector_Download
    UNUSED_SUPPLIER -> Junction
AzureFileStorageConnector_Download
    ACCOUNT_NAME = fmegrondbank
    CREDENTIAL_SOURCE = SAS
    INPUT_PORT_CONNECTED = CONNECTED
    OPERATION_TYPE = Download
    PARAMETER_SETUP = _FME_AZURE_CONTAINER_Download][{"display":"fme","value":"fme"}]]_FME_FILES_Download]@Value(_full_path)]_FME_DATA_TARGET]File]_FME_TARGET_ATTRIBUTE]<Unused>]_FME_ENCODING_TYPE]<Unused>]_FME_TARGET_FOLDER]@Value(DoelPath)]_FME_HANDLE_EXISTING_FILE_Download]Overwrite]_FME_INCLUDE_SUBFOLDERS_Download]<Unused>]_FME_ATTRIBUTES_TO_ADD_Download]_download_path]_FME_ATTRIBUTES_TO_ADD]_download_path]_FME_AZURE_CONTAINER][{"display":"fme","value":"fme"}]]_FME_FILES]@Value(_full_path)]_FME_HANDLE_EXISTING_FILE]Overwrite
    _FME_ATTRIBUTES_TO_ADD = _download_path
    _FME_ATTRIBUTES_TO_ADD_Download = _download_path
    _FME_AZURE_CONTAINER = [{"display":"fme","value":"fme"}]
    _FME_AZURE_CONTAINER_Download = [{"display":"fme","value":"fme"}]
    _FME_AZURE_SAS_TOKEN = $(SAS_fmegrondbank)
    _FME_DATA_TARGET = File
    _FME_FILES = @Value(_full_path)
    _FME_FILES_Download = @Value(_full_path)
    _FME_HANDLE_EXISTING_FILE = Overwrite
    _FME_HANDLE_EXISTING_FILE_Download = Overwrite
    _FME_TARGET_FOLDER = @Value(DoelPath)
    -> AttributeCreator_4
AttributeCreator_4
    ATTR_TABLE = SET_TO filecopy_source_dataset (varchar(200)) = @Value(_download_path)
    INPUT_PORT_CONNECTED = CONNECTED
    -> FeatureWriter [Output]
FeatureWriter
    CONFIG_PARAMETERS = ESCAPE_COMMAS_IN_FTP_FORMAT_PARAMETERS,no
    DATASET = @Value(DoelZip)
    DATASET_ATTR = _dataset
    FEATURE_TYPE_LIST_ATTR = _feature_types
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FEATURE_TYPE_NAMES_AS_FOLDERS = NO
    FILECOPY_FILE_OPERATION = COPY
    FILECOPY_MIME_TYPE = application/pdf
    FILECOPY_OVERWRITE_FILE = YES
    FORMAT = FILECOPY
    TOTAL_FEATURES_WRITTEN_ATTR = _total_features_written
    SUMMARY -> FeatureMerger_5 [REQUESTOR]
    SUMMARY -> GKB_EmailGenerator
Note: Rapportage
Junction
    -> AttributeCreator_LOGMESSAGE_Ontbrekende_bonnen_log_volgorde_4

Bookmark: COPY log en input bestanden naar runmap
FeatureMerger_4
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeRenamer
AttributeRenamer
    ATTR_TABLE = RENAME_SET_DEFAULT _dataset > filecopy_source_dataset
    KEEP_RENAMED_ONLY = no
    MISSING_INPUT_ATTRS = REMOVE
    -> FeatureWriter_COPY_LOG [Merged]
FeatureWriter_COPY_LOG
    CONFIG_PARAMETERS = ESCAPE_COMMAS_IN_FTP_FORMAT_PARAMETERS,no
    DATASET = @Value(_feature_types{0}.DoelPath)
    DATASET_ATTR = _dataset
    FEATURE_TYPE_LIST_ATTR = _feature_types
    FILECOPY_COORDINATE_SYSTEM_GRANULARITY = FEATURE
    FILECOPY_COPY_SOURCE_DIRECTORY = NO
    FILECOPY_COPY_SUBDIRECTORIES = NO
    FILECOPY_DESTINATION_DATASETTYPE_VALIDATION = Yes
    FILECOPY_FAIL_INVALID_DESTINATION = NO
    FILECOPY_FAIL_NONEXISTENT_SOURCE = NO
    FILECOPY_FEATURE_TYPE_NAMES_AS_FOLDERS = NO
    FILECOPY_FILE_OPERATION = COPY
    FILECOPY_MIME_TYPE = text/html
    FILECOPY_OVERWRITE_FILE = YES
    FORMAT = FILECOPY
    MORE_SUMMARY_ATTRS = _feature_types{0}.DoelPath
    TOTAL_FEATURES_WRITTEN_ATTR = _total_features_written
    SUMMARY -> AttributeCreator_filecopy_source_dataset
AttributeCreator_filecopy_source_dataset
    ATTR_TABLE = SET_TO filecopy_source_dataset (varchar(200)) = $(Factuur_XLSX)
    INPUT_PORT_CONNECTED = CONNECTED
    -> FeatureWriter_COPY_FACTUUR_XLSX [Summary]
FeatureWriter_COPY_FACTUUR_XLSX
    CONFIG_PARAMETERS = ESCAPE_COMMAS_IN_FTP_FORMAT_PARAMETERS,no
    DATASET = @Value(_feature_types{0}._feature_types{0}.DoelPath)
    DATASET_ATTR = _dataset
    FEATURE_TYPE_LIST_ATTR = _feature_types
    FILECOPY_COORDINATE_SYSTEM_GRANULARITY = FEATURE
    FILECOPY_COPY_SOURCE_DIRECTORY = NO
    FILECOPY_COPY_SUBDIRECTORIES = NO
    FILECOPY_DESTINATION_DATASETTYPE_VALIDATION = Yes
    FILECOPY_FAIL_INVALID_DESTINATION = NO
    FILECOPY_FAIL_NONEXISTENT_SOURCE = NO
    FILECOPY_FEATURE_TYPE_NAMES_AS_FOLDERS = NO
    FILECOPY_FILE_OPERATION = COPY
    FILECOPY_MIME_TYPE = application/vnd.openxmlformats-officedocument.spreadsheetml.sheet
    FILECOPY_OVERWRITE_FILE = YES
    FORMAT = FILECOPY
    MORE_SUMMARY_ATTRS = _feature_types{0}._feature_types{0}.DoelPath
    TOTAL_FEATURES_WRITTEN_ATTR = _total_features_written
    SUMMARY -> AttributeCreator_filecopy_source_dataset_2
AttributeCreator_filecopy_source_dataset_2
    ATTR_TABLE = SET_TO filecopy_source_dataset (varchar(200)) = $(Bonnen_XLSX)
    INPUT_PORT_CONNECTED = CONNECTED
    -> FeatureWriter_COPY_FACTUUR_XLSX_2 [Summary]
FeatureWriter_COPY_FACTUUR_XLSX_2
    CONFIG_PARAMETERS = ESCAPE_COMMAS_IN_FTP_FORMAT_PARAMETERS,no
    DATASET = @Value(_feature_types{0}._feature_types{0}._feature_types{0}.DoelPath)
    DATASET_ATTR = _dataset
    FEATURE_TYPE_LIST_ATTR = _feature_types
    FILECOPY_COORDINATE_SYSTEM_GRANULARITY = FEATURE
    FILECOPY_COPY_SOURCE_DIRECTORY = NO
    FILECOPY_COPY_SUBDIRECTORIES = NO
    FILECOPY_DESTINATION_DATASETTYPE_VALIDATION = Yes
    FILECOPY_FAIL_INVALID_DESTINATION = NO
    FILECOPY_FAIL_NONEXISTENT_SOURCE = NO
    FILECOPY_FEATURE_TYPE_NAMES_AS_FOLDERS = NO
    FILECOPY_FILE_OPERATION = COPY
    FILECOPY_MIME_TYPE = application/vnd.openxmlformats-officedocument.spreadsheetml.sheet
    FILECOPY_OVERWRITE_FILE = YES
    FORMAT = FILECOPY
    TOTAL_FEATURES_WRITTEN_ATTR = _total_features_written

Bookmark: Documentation
Note: 17-12-2025 / - Rapportage (log) opslaan in run. / - Iedere run een aparte map . Datum in mapnaam zetten / - Per ongemachted artikel de aantallen en de hoeveelheid / - Voor projectomschrijving de werklocatie code en omschrivjing gebruiken / 18-12-2026 / - HTML LOG en inputbestand in runmap zetten / Te doen: / - Opschonen als er meer dan 10 runs zijn. Gebruik datum in mapnaam. Kan pas met versie 2025.2 met REST API v4 en HTTPcaller. / 23-01-2026: v2 input bestanden in resources-data zetten vanwege read errors als ze in de repository staan. Dit gaat niet goed met de templatefile. Artikeltabel en invulbald staan beide in de repository.

FME custom transformer UniqueValueLogger
This transformer lists all unique values for a chosen attribute, along with a count of the number of occurrences for each value. The information is logged in both the Translation Window/Workspace log file and stored in attributes.
This transformer is useful when creating a workspace, and you need to know the possible values to use in a filter.
Input Ports
Input: This transformer accepts any features with an attribute.
Output Ports
Output: Features are output with the attribute selected as the unique value to filter, and a new attribute containing the number of occurrences of each unique value. All other attributes are removed. 
_count: Number of occurrences of each unique value.
_value: Unique values of selected attribute.
Parameters
Attribute to Analyze: Select the attribute for the transformer to run analysis on. 
Notes
Transformer alternatives:
Duplicate Filter - Consider using this transformer if you are looking to get a list of unique values and do not need a _count attribute 
StatisticsCalculator - Setting the Group By mode to the attribute to analyze will produce the same result as this transformer. It may be useful if you would like to gather other statistics, as well as the count of the unique attributes.

Parameters:
- VAL =   # Attribute to Analyze

Input (input)
    -> AttributeCreator

Bookmark: Count unique attribute values
AttributeCreator
    ATTR_TABLE = SET_TO _value (varchar(200)) = $(VAL)
    -> AttributeKeeper
Note: Remove unwanted / attributes
AttributeKeeper
    CREATE_BULK_MODE_FEATURES = NO
    KEEP_ATTRS = _value
    -> Aggregator
Note: Create aggregates of / features, grouped by / the target attribute value
Aggregator
    ACCUM_ATTRS = All
    AGGREGATE_TYPE = Homogeneous Collection (If Possible)
    COUNT_ATTR = _count
    GROUP_BY = _value
    MODE = Geometry - Assemble One Level
    SEP = ,
    AGGREGATE -> StringConcatenator
Note: Concatenate unique values / with their occurrence counts
StringConcatenator
    ACTION = Create New Attribute
    PARM_LINE = fme_basicstring:14%1%14%1:@Value(_value),@Value(_count)
    VAL_ATTR = _concatenated
    -> Sorter
Note: Sort output based on / occurrence count and / attribute value
Sorter
    SORT_PARM = _count NUMERIC DESCENDING NON_VALUES_AFTER_VALUES _value ALPHA ASCENDING NON_VALUES_BEFORE_VALUES
    SORTED -> ListBuilder
    SORTED -> AttributeManager

Bookmark: Create output
AttributeManager
    ATTR_TABLE = REMOVE _concatenated (buffer)
    -> Output (output)
Output (output)

Bookmark: Log unique attribute values
Note: Turn all input features / Into a single list
ListBuilder
    LIST_NAME = _list
    -> ListConcatenator
Note: Concatenate values of / the list into an attribute
ListConcatenator
    DROP_EMPTY_PARTS = No
    LIST_ATTR = _list{}._concatenated
    VAL_ATTR = UNIQUE VALUES
    -> StringConcatenator_2
Note: Add header
StringConcatenator_2
    ACTION = Create New Attribute
    PARM_LINE = "\n\nVALUE, COUNT\n@Value(UNIQUE VALUES)\n"
    VAL_ATTR = UNIQUE VALUES
    -> AttributeRemover_2
Note: Remote the list
AttributeRemover_2
    LIST_ATTRS = _list{}
    -> Logger
Note: Log the single feature / that contains the / output attribute
Logger
    LOG_FEATURE = LOG_RECORD
    MAXCOORDS = 1
    MAXFEATS = 1
    MESSAGE = Unique values:
    SEVERITY = INFO

FME custom transformer AttributeCombiner
Combines specified attribute(s) of multiple features to form concatenated string(s). This transformer outputs a single feature for each group of input features, and the specified attribute(s) in the output feature will store the concatenated string(s). 
    This transformer always discards <null> and <missing> attributes. Regarding the empty string, you can control how to handle that with the "Drop Empty String" parameter. 
    The function is similar to the "Attributes to Concatenate" option of the Aggregator, but this transformer does not aggregate features. The geometry and unspecified attributes of any one feature for each group will be preserved, but others will be discarded. 
    This transformer can be used to concatenate specific attributes of many features efficiently, if you don't need to perform feature aggregation.
    Note: This transformer contains a Python script, which was tested with both Python 2.7 and Python 3.x interpreters.
Parameters
    Group By
    : 
    If you specify one or more attributes in this parameter, the concatenation will be performed for each group of features which have the same value(s) for the specified attribute(s).
    Input is Ordered by Group
    :
    If you are sure that the input features are sorted by the "Group By" attributes, you can set "Yes" to this parameter so that the processing will be performed with the best performance.
    Attributes to Combine
    :
    Select attributes that should be combined.
    Maximum Number of Features to Combine
    :
    Optionally you can specify the maximum number of features to combine into one. The number must be an integer greater than 0. Otherwise, the setting will be ignored. 
    Note that the number specified with this parameter indicates the maximum number of processed features at once. The number of concatenated attributes could be less than the maximum, since <null> and <missing> (and <empty> if you set "Yes" to the "Drop Empty String" parameter) attributes will be discarded. 
    Drop Empty String
    :
    By default, this transformer treats the empty string as a valid value which should be concatenated. If you don't want to concatenate empty strings, set "Yes" to this parameter.
    Delimiter String
    :
    Specify a character string that should be used as a delimiter string to separate individual values. You can also leave blank this parameter not to use any delimiter.
    Surround Each Value With
    :
    Optionally you can select a pair of symbols (e.g. single quotation marks) that will surround each value before concatenating. 
    Prefix for Each Value
    : 
    Optionally you can specify a prefix string that will be added to each value. 
    Suffix for Each Value
    : 
    Optionally you can specify a suffix string that will be added to each value.

Parameters:
- GROUP_BY =   # " " Group By
- ORDERED_BY_GROUP = No   # Input is Ordered by Group
- ATTRS =   # " " Attributes to Combine
- MAX_NUM =   # Maximum Number of Features to Combine
- DROP_EMPTY = No   # Drop Empty String
- DELIM = ,   # " " Delimiter String
- QUOT = None
- PREFIX =   # " " Prefix for Each Value
- SUFFIX =   # " " Suffix for Each Value

Input (input)
    -> ParameterFetcher
ParameterFetcher
    ATTR_LIST = __tmp.group_by $(GROUP_BY) __tmp.attrs $(ATTRS) __tmp.max_num $(MAX_NUM) __tmp.delim $(DELIM) __tmp.drop_empty $(DROP_EMPTY) __tmp.quot $(QUOT) __tmp.prefix $(PREFIX) __tmp.suffix $(SUFFIX)
    -> TclCaller
TclCaller
    NEW_ATTRIBUTES = __tmp.attr{}
    SRC:
      proc preProcessToCombine {} {
          set i 0
          foreach attr [FME_GetAttribute "__tmp.attrs"] {
              FME_SetAttribute "__tmp.attr{$i}" $attr
              incr i
          }
          set num [FME_GetAttribute "__tmp.max_num"]
          if {![string is integer -strict $num]} {
              FME_SetAttribute "__tmp.max_num" 0
          }
          set group {}
          foreach attr [FME_GetAttribute "__tmp.group_by"] {
              if {![FME_AttributeExists $attr]} {
                  lappend group "\a"
              } elseif {[FME_IsAttributeNull $attr]} {
                  lappend group "\b"
              } else {
                  lappend group [FME_GetAttribute $attr]
              }
          }
          return [join $group {_}]
      }
    TCLPROG = preProcessToCombine
    VAL_ATTR = __tmp.group
    -> Tester
Tester
    BOOL_OP = OR
    TEST_CLAUSE:
      TEST @Value(__tmp.group_by) = ""
      TEST $(ORDERED_BY_GROUP) = Yes
    TEST_MODE = Automatic
    PASSED -> PythonCaller
    FAILED -> Sorter
Sorter
    SORT_PARM = __tmp.group ALPHA ASCENDING
    SORTED -> PythonCaller
PythonCaller
    PYTHONSOURCE:
      # 2016-04-13, Takashi Iijima, Original Implementation
      # 2018-05-07, Takashi Iijima, Suuports Python 3.x
      # 2020-01-13, Takashi Iijima, Changed Default Python Interpreter to 3.6+, saved with FME 2017.1.2.1

      import fme
      import fmeobjects, locale

      class AttributeCombiner(object):
          def __init__(self):
              import platform
              vt = platform.python_version_tuple()
              if vt[0] == '2':
                  loc = locale.getdefaultlocale()
                  enc = loc[1] if loc else 'utf_8'
                  self.toStr = lambda s: s.encode(enc) if isinstance(s, unicode) else str(s)
              else:
                  self.toStr = lambda s: s
              self.reset(None, None)

          def reset(self, group, feature):
              self.group = group # group ID value
              self.feature = feature # first feature for each group
              self.data = {} # key: attribute name, value: list of attribute values
              self.count = 0 # counter for number of features to combine

          def input(self, feature):
              group = feature.getAttribute('__tmp.group')
              num = int(feature.getAttribute('__tmp.max_num'))
              if group != self.group or (0 < num and num <= self.count):
                  self.output()
                  self.reset(group, feature)
              for attr in feature.getAttribute('__tmp.attr{}'):
                  attr = self.toStr(attr)
                  isNull, isMissing, type = feature.getAttributeNullMissingAndType(attr)
                  if not isNull and not isMissing:
                      self.data.setdefault(attr, []).append('%s' % feature.getAttribute(attr))
              self.count += 1

          def close(self):
              self.output()

          def output(self):
              if self.feature:
                  fmt = self.getFormat()
                  delim = self.feature.getAttribute('__tmp.delim')
                  if self.feature.getAttribute('__tmp.drop_empty') == 'Yes':
                      for attr, values in self.data.items():
                          self.feature.setAttribute(attr, delim.join([fmt % v for v in values if v != '']))
                  else:
                      for attr, values in self.data.items():
                          self.feature.setAttribute(attr, delim.join([fmt % v for v in values]))
                  self.pyoutput(self.feature)

          def getFormat(self):
              formats = {
                  'Single': '\'%s%%s%s\'' ,
                  'Double': '"%s%%s%s"' ,
                  'Round': '(%s%%s%s)',
                  'Curly': '{%s%%s%s}',
                  'Square': '[%s%%s%s]',
                  'Inequality': '<%s%%s%s>',
                  'None': '%s%%s%s'
              }
              option = self.feature.getAttribute('__tmp.quot')
              prefix= self.feature.getAttribute('__tmp.prefix')
              suffix = self.feature.getAttribute('__tmp.suffix')
              return formats[option] % (prefix, suffix)
    PYTHONSYMBOL = AttributeCombiner
    -> AttributeRemover
AttributeRemover
    LIST_ATTRS = __tmp.attr{}
    REMOVE_ATTRS = __tmp.attrs,__tmp.delim,__tmp.drop_empty,__tmp.group,__tmp.group_by,__tmp.max_num,__tmp.prefix,__tmp.quot,__tmp.suffix
    -> Output (output)
Output (output)

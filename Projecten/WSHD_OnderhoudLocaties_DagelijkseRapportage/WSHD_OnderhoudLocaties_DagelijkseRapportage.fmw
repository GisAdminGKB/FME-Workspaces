FME workspace WSHD_OnderhoudLocaties_DagelijkseRapportage.fmw
Title: WSHD_DeurInspecties
Description: WSHD_DeurInspecties

Parameters:
- WVB_EMAIL = bas@gkbgroep.nl   # Email werkvoorbereider
- TypeRun = LocatieUpdate   # Locatie update,LocatieUpdate%Rapportage,Rapportage Type run

Readers:
- SAFE.ESRI-AGOL.ARCGISFEATURESERVICE_3: SAFE.ESRI-AGOL.ARCGISFEATURESERVICE
- SAFE.ESRI-AGOL.ARCGISFEATURESERVICE_2: SAFE.ESRI-AGOL.ARCGISFEATURESERVICE
- SAFE.ESRI-AGOL.ARCGISFEATURESERVICE_8: SAFE.ESRI-AGOL.ARCGISFEATURESERVICE

Writers:
- SAFE.ESRI-AGOL.ARCGISFEATURESERVICE_1: SAFE.ESRI-AGOL.ARCGISFEATURESERVICE
- SAFE.ESRI-AGOL.ARCGISFEATURESERVICE_6: SAFE.ESRI-AGOL.ARCGISFEATURESERVICE
- SAFE.ESRI-AGOL.ARCGISFEATURESERVICE_4: SAFE.ESRI-AGOL.ARCGISFEATURESERVICE
- SAFE.ESRI-AGOL.ARCGISFEATURESERVICE_7: SAFE.ESRI-AGOL.ARCGISFEATURESERVICE
- SAFE.ESRI-AGOL.ARCGISFEATURESERVICE_9: SAFE.ESRI-AGOL.ARCGISFEATURESERVICE

Note: f / json / portalUrl / https://www.arcgis.com / utcOffset / ||+02:00 / locale / ||en / queryParameters / {"objectIds":"7","orderByFields":"||EditDate DESC, objectid ASC"} / templateItemId / 9a851247954d45e889b881ed29f6774a / outputReportName / WSHD_DeurInspecties_voorbeeldRapport_OID7_20250618164128 / surveyItemId / c091b074008049668defe946aecd3532 / featureLayerUrl / https://services9.arcgis.com/CjT8oELYhF7fnj6q/arcgis/rest/services/service_008f1297e1954ca8acdfdc78c9b1a2d9/FeatureServer/0 / uploadInfo / {"type":"arcgis","parameters":{"folderId":"78a11498ae4b4e539a32e7d582efe4d0"},"conflictBehavior":"rename"} / outputFormat / pdf / outputPackageName / WSHD_DeurInspecties_voorbeeldRapport_OID7_20250618164128 / token / 3NKHt6i2urmWtqOuugvr9SKs6o-wsD1DHTvM96YfQVsO0u-leMI6rB6HjIWOfs2JGmIZUe5u-MvTim3gYWQu_9LiolShjonFpYdYfUyI9p0w_OQmsVboZX16-n7Ht1Que20c3n_KhYU-sqBdgNgZQkfmFEakY7k3qOAgxhvcP0_1E3YGnMZpPlu9aPgE1dnZKpiYa8ReMYagVqP410XMUdHzwkI8gLVCZGfvXRV4DwA.
Junction_6
    -> AttributeCreator__Datum_milliseconds_to_seconds_2

Bookmark: LEES Bronnen
WSHD_DL_OnderhoudsLocaties (reader SAFE.ESRI-AGOL.ARCGISFEATURESERVICE_2)
    attributes: Code String(50), Naam String(100), Functie String(50), AantalDeuren SmallInteger, DatumDeurInspectie Date, Bron String(255), OBJECTID OID, GlobalID GlobalID(38), InspectieStatus String(256), ZoekTekst String(256), DeurInspectiePlanDatum Date, AantalDeurinspectiesDitJaar String(256), Dakonderhoud String(50), Deurinspectie String(50), StatusDakonderhoud String(50)
    -> Junction_4
    -> DuplicateFilter
Junction_4
    -> TestFilter_Deurinspectie_van_toepassing
    -> TestFilter_dakonderhoud_van_toepassing
    -> AttributeKeeper_11
TestFilter_Deurinspectie_van_toepassing
    DEFAULT_VALUE = Locatie zonder deurinspectie(s)
    PASSED_TEST_GROUP_OUTPUT = FIRST
    TEST_LIST = "BOOL_OP,OR,COMPOSITE_TEST,""""""1"""""",TEST_CLAUSE,TEST @Value(Deurinspectie) = Ja",Locatie met deurinspectie(s)
    Locatie met deurinspectie(s) -> TestFilter_5
TestFilter_5
    DEFAULT_VALUE = <UNFILTERED>
    PASSED_TEST_GROUP_OUTPUT = FIRST
    TEST_LIST = "BOOL_OP,OR,COMPOSITE_TEST,""""""1"""""",TEST_CLAUSE,TEST @Value(InspectieStatus) != Vervallen",@Value(InspectieStatus) != Vervallen
    @Value(InspectieStatus) != Vervallen -> FeatureMerger_3 [REQUESTOR]
TestFilter_dakonderhoud_van_toepassing
    DEFAULT_VALUE = Locatie zonder dakonderhoud
    PASSED_TEST_GROUP_OUTPUT = FIRST
    TEST_LIST = "BOOL_OP,OR,COMPOSITE_TEST,""""""1"""""",TEST_CLAUSE,TEST @Value(Dakonderhoud) = Ja",Locatie met dakonderhoud
    Locatie met dakonderhoud -> Junction_2
WSHD_DL_Deurinspectie (reader SAFE.ESRI-AGOL.ARCGISFEATURESERVICE_3)
    attributes: objectid OID, globalid GlobalID(38), LocatieType String(255), LocatieNaam String(255), DeurNummer String(255), DeurType String(255), QRDeur String(255), DeurData String(255), Opdrachtgever String(255), ProjectCode String(255), ProjectOmschrijving String(255), Scharnieren String(255), Ramen String(255), Bodemrubber String(255), Secties String(255), Looprollen String(255), Afdichtingrubbers String(255), Staalkabels String(255), Lagerplaten String(255), Torsieveren String(255), Veerbreukbeveiliging String(255), Rails String(255), Electrisch String(255), Deurdranger String(255), Loopdeurslot String(255), Schuifgrendel String(255), Reparatie String(255), ReparatieOmschrijving String(255), ReparatieVerbruik String(255), ReparatieTijd Integer,
      Bijzonderheden String(255), InspectieStatus String(255), Inspecteur String(255), AdresLabel String(255), LocatieCode String(255), Point_WKT String(255), InspectieDatum Date, InspectieTijd String(255), CreationDate Date, Creator String(128), EditDate Date, Editor String(128), Rollen String(256), Muurbeugels String(256), Lamellen String(256), Bak String(256), Eindnokken String(256), HeeftLoopDeur String(256), StatusQRCode String(256), Gerapporteerd String(256), RapportageDatum Date, InspectieType String(50), Uren Double, Reisuren Double, Kilometers Integer, InspectieJaar Integer, Herzien String(50), DeurGoedgekeurd String(50)
    -> TestFilter_velden_gevuld
WSHD_DL_Dakonderhoud (reader SAFE.ESRI-AGOL.ARCGISFEATURESERVICE_8)
    attributes: ProjectCode String(255), ProjectOmschrijving String(255), TypeOnderhoud String(50), LocatieCode String(255), LocatieNaam String(255), LocatieType String(255), Bijzonderheden String(255), DatumDakonderhoud Date, TijdstipDakonderhoud String(255), StatusDakonderhoud String(255), OnderhoudsMedewerker String(255), ExtraWerkzaamheden String(255), OmschrijvingExtraWerkzaamheden String(255), VerbruikExtraWerkzaamheden String(255), AdresLabel String(255), JaarOnderhoud Integer, Kilometers Integer, Reisuren Double, Uren Double, RapportageDatum Date, GlobalID GlobalID(38), OBJECTID OID, CreationDate Date, Creator String(128), EditDate Date, Editor String(128), Gerapporteerd String(50), AantalFotos Integer
    -> TestFilter_velden_gevuld_2
TestFilter_8
    DEFAULT_VALUE = Rapportage
    PASSED_TEST_GROUP_OUTPUT = FIRST
    TEST_LIST = "BOOL_OP,OR,COMPOSITE_TEST,""""""1"""""",TEST_CLAUSE,TEST $(TypeRun) = LocatieUpdate",LocatieUpdate
    LocatieUpdate -> Junction_6
    LocatieUpdate -> Junction_5
    Rapportage -> AttributeCreator__Datum_milliseconds_to_seconds
    Rapportage -> Junction_6
    Rapportage -> Junction_5
Junction_5
    -> AttributeCreator__Datum_milliseconds_to_seconds_5
Junction
    -> AttributeCreator__Datum_milliseconds_to_seconds_3
    -> FeatureMerger_6 [SUPPLIER]
    -> AttributeCreator__Datum_milliseconds_to_seconds_5

Bookmark: Verwerken dakonderehoud
Note: WSHD_DL_OnderhoudsLocaties
Junction_2
    -> AttributeKeeper_7
AttributeKeeper_7
    CREATE_BULK_MODE_FEATURES = NO
    KEEP_ATTRS = Code,GlobalID,Naam
    -> FeatureMerger_4 [SUPPLIER]
AttributeCreator__Datum_milliseconds_to_seconds_3
    ATTR_TABLE:
      SET_TO Datum (real64) = @Evaluate(@Value(CreationDate)/1000)
      SET_TO Vandaag (varchar(200)) = @DateTimeFormat(@DateTimeNow(),%Y%m%d)
      SET_TO JaarVandaag (int32) = @DateTimeFormat(@DateTimeNow(),%Y)
    -> DateTimeConverter_11
DateTimeConverter_11
    DATETIME_ATTR = Datum
    IN_FORMAT = %s$
    OUT_FORMAT = %Y%m%d
    PASSTHROUGH = NO
    REPAIR_INPUT = YES
    -> TestFilter_TypeRun
TestFilter_TypeRun
    DEFAULT_VALUE = Rapportage
    PASSED_TEST_GROUP_OUTPUT = FIRST
    TEST_LIST = "BOOL_OP,OR,COMPOSITE_TEST,""""""1"""""",TEST_CLAUSE,TEST $(TypeRun) = LocatieUpdate",LocatieUpdate
    LocatieUpdate -> Sorter_2
    Rapportage -> TestFilter_10
    Rapportage -> AttributeCombiner_3
    Rapportage -> Sorter_2
TestFilter_10
    DEFAULT_VALUE = Al gerapporteerd
    PASSED_TEST_GROUP_OUTPUT = FIRST
    TEST_LIST:
      "BOOL_OP,OR,COMPOSITE_TEST,""""""1 OR 2 OR 3 OR 4"""""",TEST_CLAUSE,TEST @Value(Gerapporteerd) = Nee
      TEST @Value(Gerapporteerd) = Gewijzigd
      TEST Gerapporteerd ATTRIBUTE_VALUE_NULL ""
      TEST Gerapporteerd ATTRIBUTE_IS_EMPTY """,Nog niet gerapporteerd of gewijzigd
    Nog niet gerapporteerd of gewijzigd -> Sorter_op_Datum_4
FeatureMerger_4
    ATTR_ACCUM_MODE = Merge Supplier
    ATTR_CONFLICT_RES_LOOKUP = REQUESTOR_IF_CONFLICT
    IGNORE_NULLS = No
    JOIN_KEYS = @Value(LocatieCode) @Value(Code) AUTO @Value(LocatieNaam) @Value(Naam) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeKeeper_8
AttributeKeeper_8
    CREATE_BULK_MODE_FEATURES = NO
    KEEP_ATTRS = GlobalID,StatusDakonderhoud
    -> Junction_3
Note: UPDATE Locaties
Junction_3
    -> WSHD_DL_OnderhoudsLocaties (writer SAFE.ESRI-AGOL.ARCGISFEATURESERVICE_9)
WSHD_DL_OnderhoudsLocaties (writer SAFE.ESRI-AGOL.ARCGISFEATURESERVICE_9)
    attributes: StatusDakonderhoud String(255), GlobalID GlobalID(38)

Bookmark: DEURINSPECTIES
AttributeKeeper_11
    CREATE_BULK_MODE_FEATURES = NO
    KEEP_ATTRS = Code,GlobalID,Naam
    -> FeatureMerger_7 [SUPPLIER]
AttributeCreator__Datum_milliseconds_to_seconds_5
    ATTR_TABLE:
      SET_TO Datum (varchar(200)) = FME_CONDITIONAL:DEFAULT_VALUE'@Evaluate(@Value(DatumDakonderhoud)/1000)'BOOL_OP;OR;COMPOSITE_TEST;1;TEST @Value(fme_feature_type) = WSHD_DL_Deurinspectie'@Evaluate(@Value(InspectieDatum)/1000)'FME_NUM_CONDITIONS2___
      SET_TO Vandaag (varchar(200)) = @DateTimeFormat(@DateTimeNow(),%Y%m%d)
    -> Sorter
Sorter
    SORT_PARM = fme_feature_type NATURAL ASCENDING LocatieCode NATURAL ASCENDING Datum NATURAL DESCENDING
    SORTED -> DateTimeConverter_12
DateTimeConverter_12
    DATETIME_ATTR = Datum
    IN_FORMAT = %s$
    OUT_FORMAT = %Y%m%d
    PASSTHROUGH = NO
    REPAIR_INPUT = YES
    -> Counter
Counter
    CNT_ATTR = _count
    GROUP_BY = fme_feature_type LocatieCode
    SCOPE = Local
    START = 1
    -> TestFilter_count_1__datum_ouder_dan_6_maanden
TestFilter_count_1__datum_ouder_dan_6_maanden
    DEFAULT_VALUE = Rest
    PASSED_TEST_GROUP_OUTPUT = FIRST
    TEST_LIST:
      "BOOL_OP,AND,COMPOSITE_TEST,""""""1 AND 2"""""",TEST_CLAUSE,TEST @Value(_count) = 1
      TEST @DateTimeDiff(@Value(Vandaag),@Value(Datum), Months) > 6",Nieuwste datum van iedere groep
    Nieuwste datum van iedere groep -> AttributeManager_13
AttributeManager_13
    ATTR_TABLE:
      SET_TO InspectieStatus (varchar(255)) = FME_CONDITIONAL:DEFAULT_VALUE'_FME_NO_OP_'BOOL_OP;OR;COMPOSITE_TEST;1;TEST @Value(fme_feature_type) = WSHD_DL_Deurinspectie'Uitvoeren'FME_NUM_CONDITIONS2___
      SET_TO StatusDakonderhoud (varchar(255)) = FME_CONDITIONAL:DEFAULT_VALUE'_FME_NO_OP_'BOOL_OP;OR;COMPOSITE_TEST;1;TEST @Value(fme_feature_type) = WSHD_DL_Dakonderhoud'Uitvoeren'FME_NUM_CONDITIONS2___
      REMOVE Datum (date)
      REMOVE Vandaag (varchar(200))
      REMOVE objectid (int32)
      REMOVE LocatieType (varchar(255))
      REMOVE globalid (varchar(38))
      REMOVE DeurNummer (varchar(255))
      REMOVE DeurType (varchar(255))
      REMOVE QRDeur (varchar(255))
      REMOVE DeurData (varchar(255))
      REMOVE Opdrachtgever (varchar(255))
      REMOVE ProjectCode (varchar(255))
      REMOVE ProjectOmschrijving (varchar(255))
      REMOVE Scharnieren (varchar(255))
      REMOVE Ramen (varchar(255))
      REMOVE Bodemrubber (varchar(255))
      REMOVE Secties (varchar(255))
      REMOVE Looprollen (varchar(255))
      REMOVE Afdichtingrubbers (varchar(255))
      REMOVE Staalkabels (varchar(255))
      REMOVE Lagerplaten (varchar(255))
      REMOVE Torsieveren (varchar(255))
      REMOVE Veerbreukbeveiliging (varchar(255))
      REMOVE Rails (varchar(255))
      REMOVE Electrisch (varchar(255))
      REMOVE Deurdranger (varchar(255))
      REMOVE Loopdeurslot (varchar(255))
      REMOVE Schuifgrendel (varchar(255))
      REMOVE Reparatie (varchar(255))
      REMOVE ReparatieOmschrijving (varchar(255))
      REMOVE ReparatieVerbruik (varchar(255))
      REMOVE ReparatieTijd (int32)
      REMOVE Bijzonderheden (varchar(255))
      REMOVE Inspecteur (varchar(255))
      REMOVE AdresLabel (varchar(255))
      REMOVE Point_WKT (varchar(255))
      REMOVE InspectieDatum (int64)
      REMOVE InspectieTijd (varchar(255))
      REMOVE CreationDate (int64)
      REMOVE Creator (varchar(128))
      REMOVE EditDate (int64)
      REMOVE Editor (varchar(128))
      REMOVE Rollen (varchar(256))
      REMOVE Muurbeugels (varchar(256))
      REMOVE Lamellen (varchar(256))
      REMOVE Bak (varchar(256))
      REMOVE Eindnokken (varchar(256))
      REMOVE HeeftLoopDeur (varchar(256))
      REMOVE StatusQRCode (varchar(256))
      REMOVE Gerapporteerd (varchar(256))
      REMOVE RapportageDatum (int64)
      REMOVE InspectieType (varchar(50))
      REMOVE Uren (real64)
      REMOVE Reisuren (real64)
      REMOVE Kilometers (int32)
      REMOVE InspectieJaar (int32)
      REMOVE Herzien (varchar(50))
      REMOVE DeurGoedgekeurd (varchar(50))
      REMOVE fme_feature_type (varchar(50))
      REMOVE TypeOnderhoud (varchar(50))
      REMOVE DatumDakonderhoud (int64)
      REMOVE TijdstipDakonderhoud (varchar(255))
      REMOVE OnderhoudsMedewerker (varchar(255))
      REMOVE ExtraWerkzaamheden (varchar(255))
      REMOVE OmschrijvingExtraWerkzaamheden (varchar(255))
      REMOVE VerbruikExtraWerkzaamheden (varchar(255))
      REMOVE JaarOnderhoud (int32)
      REMOVE GlobalID (varchar(38))
      REMOVE OBJECTID (int32)
      REMOVE AantalFotos (int32)
      REMOVE arcgisfeatureservice_feature_url (buffer)
      REMOVE _count (int64)
    -> FeatureMerger_7 [REQUESTOR]
FeatureMerger_7
    ATTR_ACCUM_MODE = Merge Supplier
    ATTR_CONFLICT_RES_LOOKUP = REQUESTOR_IF_CONFLICT
    IGNORE_NULLS = No
    JOIN_KEYS = @Value(LocatieCode) @Value(Code) AUTO @Value(LocatieNaam) @Value(Naam) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeKeeper_12
AttributeKeeper_12
    CREATE_BULK_MODE_FEATURES = NO
    KEEP_ATTRS = GlobalID,InspectieStatus,StatusDakonderhoud
    -> WSHD_DL_OnderhoudsLocaties (writer SAFE.ESRI-AGOL.ARCGISFEATURESERVICE_6)

Bookmark: Controle gegevens
DuplicateFilter
    INPUT_ORDERED_CHOICE_LOOKUP = NO
    KEYATTR = Code
    INPUT_ORDERED_CHOICE = No
    UNIQUE -> AttributeKeeper_13
AttributeKeeper_13
    CREATE_BULK_MODE_FEATURES = NO
    KEEP_ATTRS = Code,Functie,Naam
    -> FeatureMerger_locatie_gegevens [SUPPLIER]
TestFilter_velden_gevuld
    DEFAULT_VALUE = Velden gevuld
    PASSED_TEST_GROUP_OUTPUT = FIRST
    TEST_LIST:
      "BOOL_OP,COMPOSITE,COMPOSITE_TEST,""""""NOT ( 1 OR 2 OR 3 )"""""",TEST_CLAUSE,TEST LocatieNaam ATTRIBUTE_HAS_A_VALUE ""
      TEST LocatieType ATTRIBUTE_HAS_A_VALUE ""
      TEST AdresLabel ATTRIBUTE_HAS_A_VALUE """,Ontbrekende waarden
    Ontbrekende waarden -> NoFeaturesTester
NoFeaturesTester
    NoInput -> FeatureReader [INITIATOR]
    -> FeatureMerger_locatie_gegevens [REQUESTOR]
Note: De dataverbinding van de tablets is soms slechts of hapert waardoor de velden die middels pulldata("@layer" of geocoding gevuld worden leeg blijven. / Dat zijn de velden: / LocatieNaam / LocatieType / AdresLabel / Als een van deze velden leeg is dan alle 3 (opnieuw) vullen.
TestFilter_velden_gevuld_2
    DEFAULT_VALUE = Velden gevuld
    PASSED_TEST_GROUP_OUTPUT = FIRST
    TEST_LIST:
      "BOOL_OP,COMPOSITE,COMPOSITE_TEST,""""""NOT ( 1 OR 2 OR 3 )"""""",TEST_CLAUSE,TEST LocatieNaam ATTRIBUTE_HAS_A_VALUE ""
      TEST LocatieType ATTRIBUTE_HAS_A_VALUE ""
      TEST AdresLabel ATTRIBUTE_HAS_A_VALUE """,Ontbrekende waarden
    Ontbrekende waarden -> NoFeaturesTester_2
NoFeaturesTester_2
    NoInput -> FeatureReader_2 [INITIATOR]
    -> FeatureMerger_locatie_gegevens [REQUESTOR]
FeatureMerger_locatie_gegevens
    ATTR_ACCUM_MODE = Prefix Supplier
    IGNORE_NULLS = No
    JOIN_KEYS = @Value(LocatieCode) @Value(Code) AUTO
    MERGE_TYPE_VAL = ATTRIBUTES
    PROCESS_DUPS = NO
    REJECT_NULL_MISSING_KEYS = No
    SUPPLIERS_FIRST = No
    SUPPLIER_PREFIX = loc
    MERGE_TYPE = Attributes Only
    MERGED -> AttributeManager_16
AttributeManager_16
    ATTR_TABLE:
      SET_TO LocatieType (varchar(255)) = @Value(locFunctie)
      SET_TO LocatieNaam (varchar(255)) = @Value(locNaam)
      REMOVE locCode (varchar(50))
      REMOVE locNaam (varchar(100))
      REMOVE locFunctie (varchar(50))
    -> CoordinateExtractor
CoordinateExtractor
    IND = 0
    RECURSIVE = No
    X_ATTR = _x
    Y_ATTR = _y
    MODE = Specify Coordinate
    -> AttributeReprojector
AttributeReprojector
    DEST = LL-WGS84
    SOURCE = SPHERICAL_MERCATOR
    XATTR = _x
    YATTR = _y
    REPROJECTED -> Geocoder
Geocoder
    ARCGIS_AUTH_TYPE = web_service
    GEOCODE_SERVER_URL = https://geocode.arcgis.com/arcgis/rest/services/World/GeocodeServer
    GEOCODING_SERVICE = ArcGIS Online
    LATITUDE = @Value(_y)
    LATITUDE_ArcGIS_Online = @Value(_y)
    LONGITUDE = @Value(_x)
    LONGITUDE_ArcGIS_Online = @Value(_x)
    METHOD = reverse
    METHOD_ArcGIS_Online = reverse
    NC = Esri ArcGis Online (gisadmin)
    NC_ArcGIS_Online = Esri ArcGis Online (gisadmin)
    RETURN_JSON_RESPONSE = yes
    THREADS = 4
    TIMEOUT = 60
    VERIFY_HTTPS = yes
    -> JSONExtractor
JSONExtractor
    EXTRACT_QUERY_TABLE = AdresLabel json["address"]["LongLabel"]
    JSON_DOCUMENT = @Value(_json_response)
    READ_FROM_FILE = NO
    EVALUATED -> AttributeKeeper_14
AttributeKeeper_14
    CREATE_BULK_MODE_FEATURES = NO
    KEEP_ATTRS = AdresLabel,globalid,GlobalID,LocatieNaam,LocatieType
    -> FeatureTypeFilter
FeatureTypeFilter
    ATTRIBUTES = <Blank>,<Unfiltered>,WSHD_DL_Deurinspectie,WSHD_DL_Dakonderhoud
    ATTRIBUTE_INFO = WSHD_DL_Dakonderhoud,ProjectCode,ProjectOmschrijving,TypeOnderhoud,LocatieCode,LocatieNaam,LocatieType,Bijzonderheden,DatumDakonderhoud,TijdstipDakonderhoud,StatusDakonderhoud,OnderhoudsMedewerker,ExtraWerkzaamheden,OmschrijvingExtraWerkzaamheden,VerbruikExtraWerkzaamheden,AdresLabel,JaarOnderhoud,Kilometers,Reisuren,Uren,RapportageDatum,GlobalID,OBJECTID,CreationDate,Creator,EditDate,Editor,Gerapporteerd,AantalFotos,arcgisfeatureservice_feature_url,fme_feature_type,WSHD_DL_Deurinspectie,objectid,globalid,LocatieType,LocatieNaam,DeurNummer,DeurType,QRDeur,DeurData,Opdrachtgever,ProjectCode,ProjectOmschrijving,Scharnieren,Ramen,Bodemrubber,Secties,Looprollen,Afdichtingrubbers,Staalkabels,Lagerplaten,Torsieveren,Veerbreukbeveiliging,Rails,Electrisch,Deurdranger,Loopdeurslot,Schuifgrendel,Reparatie,ReparatieOmschrijving,ReparatieVerbruik,ReparatieTijd,Bijzonderheden,InspectieStatus,Inspecteur,AdresLabel,LocatieCode,Point_WKT,InspectieDatum,InspectieTijd,CreationDate,Creator,EditDate,Editor,Rollen,Muurbeugels,Lamellen,Bak,Eindnokken,HeeftLoopDeur,StatusQRCode,Gerapporteerd,RapportageDatum,InspectieType,Uren,Reisuren,Kilometers,InspectieJaar,Herzien,DeurGoedgekeurd,fme_feature_type
    WSHD_DL_Deurinspectie -> FeatureWriter_2 [WSHD_DL_Deurinspectie]
    WSHD_DL_Dakonderhoud -> FeatureWriter [WSHD_DL_Dakonderhoud]

Bookmark: UPDATE en opnieuw LEZEN
FeatureWriter_2
    CONFIG_PARAMETERS = ESCAPE_COMMAS_IN_FTP_FORMAT_PARAMETERS,no
    DATASET_ATTR = _dataset
    FEATURE_TYPE_LIST_ATTR = _feature_types
    FORMAT = SAFE.ESRI-AGOL.ARCGISFEATURESERVICE
    SAFE.ESRI-AGOL.ARCGISFEATURESERVICE_AGOL_AUTH_NC = Esri ArcGIS Online (gisadmin_GKB)
    SAFE.ESRI-AGOL.ARCGISFEATURESERVICE_ALWAYS_CREATE_FEATURE_TYPES = NO
    SAFE.ESRI-AGOL.ARCGISFEATURESERVICE_APPEND_FORMAT = featureCollection
    SAFE.ESRI-AGOL.ARCGISFEATURESERVICE_ASYNC_WRITE = NO
    SAFE.ESRI-AGOL.ARCGISFEATURESERVICE_ENABLE_ATTACHMENTS = NO
    SAFE.ESRI-AGOL.ARCGISFEATURESERVICE_FEATURES_PER_REQUEST = 1000
    SAFE.ESRI-AGOL.ARCGISFEATURESERVICE_FEATURE_SERVICE_HANDLING = USE_EXISTING
    SAFE.ESRI-AGOL.ARCGISFEATURESERVICE_FEATURE_SERVICE_WITH_ID = WSHD_DL_DeurInspecties(f01fe37c40a84813b1b08a50b3f00a11)
    SAFE.ESRI-AGOL.ARCGISFEATURESERVICE_FOLDER_NAME = WSHD Assets
    SAFE.ESRI-AGOL.ARCGISFEATURESERVICE_PRESERVE_GLOBALID = YES
    SAFE.ESRI-AGOL.ARCGISFEATURESERVICE_SITE_SOURCE_TYPE = USER
    SAFE.ESRI-AGOL.ARCGISFEATURESERVICE_TARGET_WKID = 102100
    SAFE.ESRI-AGOL.ARCGISFEATURESERVICE_URL_TYPE = AGOL
    SAFE.ESRI-AGOL.ARCGISFEATURESERVICE_USE_GLOBAL_ID = YES
    SAFE.ESRI-AGOL.ARCGISFEATURESERVICE_VERIFY_HTTPS = WEB_CONN
    TOTAL_FEATURES_WRITTEN_ATTR = _total_features_written
    SUMMARY -> FeatureReader [INITIATOR]
FeatureReader
    ATTRIBUTES = WSHD_DL_Deurinspectie,"objectid,globalid,LocatieType,LocatieNaam,DeurNummer,DeurType,QRDeur,DeurData,Opdrachtgever,ProjectCode,ProjectOmschrijving,Scharnieren,Ramen,Bodemrubber,Secties,Looprollen,Afdichtingrubbers,Staalkabels,Lagerplaten,Torsieveren,Veerbreukbeveiliging,Rails,Electrisch,Deurdranger,Loopdeurslot,Schuifgrendel,Reparatie,ReparatieOmschrijving,ReparatieVerbruik,ReparatieTijd,Bijzonderheden,InspectieStatus,Inspecteur,AdresLabel,LocatieCode,Point_WKT,InspectieDatum,InspectieTijd,CreationDate,Creator,EditDate,Editor,Rollen,Muurbeugels,Lamellen,Bak,Eindnokken,HeeftLoopDeur,StatusQRCode,Gerapporteerd,RapportageDatum,InspectieType,Uren,Reisuren,Kilometers,InspectieJaar,Herzien,DeurGoedgekeurd,fme_feature_type,arcgisfeatureservice_feature_url"
    ATTR_ACCUM_MODE = Only Use Result
    CLIP_TO_ENVELOPE = NO
    COMBINE_GEOM = Use Result
    FEATURETYPES = WSHD_DL_Deurinspectie
    FORMAT = SAFE.ESRI-AGOL.ARCGISFEATURESERVICE
    GEOMETRY_TYPES = WSHD_DL_Deurinspectie,""",fme_point"""
    INITIATOR_FIRST_OUTPUT = default
    INTERACT = NONE
    ORDER_RESULTS = No
    OUTPUT_ADD_SCHEMA_ATTRIBUTES = NO
    OUTPUT_FEATURES_DISPLAY = Schema and Data Features
    SAFE.ESRI-AGOL.ARCGISFEATURESERVICE_AGOL_AUTH_NC = Esri ArcGIS Online (gisadmin_GKB)
    SAFE.ESRI-AGOL.ARCGISFEATURESERVICE_ALIAS_MODE = NONE
    SAFE.ESRI-AGOL.ARCGISFEATURESERVICE_CREATE_FEATURE_TABLES_FROM_DATA = Yes
    SAFE.ESRI-AGOL.ARCGISFEATURESERVICE_FEATURES_PER_REQUEST = 1000
    SAFE.ESRI-AGOL.ARCGISFEATURESERVICE_FEATURE_SERVICE_WITH_ID = WSHD_DL_DeurInspecties(f01fe37c40a84813b1b08a50b3f00a11)
    SAFE.ESRI-AGOL.ARCGISFEATURESERVICE_FOLDER_NAME = WSHD Assets
    SAFE.ESRI-AGOL.ARCGISFEATURESERVICE_QUERY_FEATURE_TYPES_FOR_MERGE_FILTERS = Yes
    SAFE.ESRI-AGOL.ARCGISFEATURESERVICE_RESOLVE_DOMAINS = NO
    SAFE.ESRI-AGOL.ARCGISFEATURESERVICE_SAFE.ESRI-AGOL.ARCGISFEATURESERVICE_EXPOSE_FORMAT_ATTRS = fme_feature_type,String(50) arcgisfeatureservice_feature_url,String
    SAFE.ESRI-AGOL.ARCGISFEATURESERVICE_SITE_SOURCE_TYPE = USER
    SAFE.ESRI-AGOL.ARCGISFEATURESERVICE_URL_TYPE = AGOL
    SAFE.ESRI-AGOL.ARCGISFEATURESERVICE_USE_SEARCH_ENVELOPE = NO
    SAFE.ESRI-AGOL.ARCGISFEATURESERVICE_VERIFY_HTTPS = WEB_CONN
    WSHD_DL_Deurinspectie -> TestFilter_8
FeatureWriter
    CONFIG_PARAMETERS = ESCAPE_COMMAS_IN_FTP_FORMAT_PARAMETERS,no
    DATASET_ATTR = _dataset
    FEATURE_TYPE_LIST_ATTR = _feature_types
    FORMAT = SAFE.ESRI-AGOL.ARCGISFEATURESERVICE
    SAFE.ESRI-AGOL.ARCGISFEATURESERVICE_AGOL_AUTH_NC = Esri ArcGIS Online (gisadmin_GKB)
    SAFE.ESRI-AGOL.ARCGISFEATURESERVICE_ALWAYS_CREATE_FEATURE_TYPES = NO
    SAFE.ESRI-AGOL.ARCGISFEATURESERVICE_APPEND_FORMAT = featureCollection
    SAFE.ESRI-AGOL.ARCGISFEATURESERVICE_ASYNC_WRITE = NO
    SAFE.ESRI-AGOL.ARCGISFEATURESERVICE_ENABLE_ATTACHMENTS = NO
    SAFE.ESRI-AGOL.ARCGISFEATURESERVICE_FEATURES_PER_REQUEST = 1000
    SAFE.ESRI-AGOL.ARCGISFEATURESERVICE_FEATURE_SERVICE_HANDLING = USE_EXISTING
    SAFE.ESRI-AGOL.ARCGISFEATURESERVICE_FEATURE_SERVICE_WITH_ID = WSHD_DL_Dakonderhoud(1221ec2727914d979f1b4c52705c3af4)
    SAFE.ESRI-AGOL.ARCGISFEATURESERVICE_FOLDER_NAME = [{"display":"WSHD Assets","value":"WSHD Assets"}]
    SAFE.ESRI-AGOL.ARCGISFEATURESERVICE_PRESERVE_GLOBALID = YES
    SAFE.ESRI-AGOL.ARCGISFEATURESERVICE_SITE_SOURCE_TYPE = USER
    SAFE.ESRI-AGOL.ARCGISFEATURESERVICE_TARGET_WKID = 102100
    SAFE.ESRI-AGOL.ARCGISFEATURESERVICE_URL_TYPE = AGOL
    SAFE.ESRI-AGOL.ARCGISFEATURESERVICE_USE_GLOBAL_ID = YES
    SAFE.ESRI-AGOL.ARCGISFEATURESERVICE_VERIFY_HTTPS = WEB_CONN
    TOTAL_FEATURES_WRITTEN_ATTR = _total_features_written
    SUMMARY -> FeatureReader_2 [INITIATOR]
FeatureReader_2
    ATTRIBUTES = WSHD_DL_Dakonderhoud,"ProjectCode,ProjectOmschrijving,TypeOnderhoud,LocatieCode,LocatieNaam,LocatieType,Bijzonderheden,DatumDakonderhoud,TijdstipDakonderhoud,StatusDakonderhoud,OnderhoudsMedewerker,ExtraWerkzaamheden,OmschrijvingExtraWerkzaamheden,VerbruikExtraWerkzaamheden,AdresLabel,JaarOnderhoud,Kilometers,Reisuren,Uren,RapportageDatum,GlobalID,OBJECTID,CreationDate,Creator,EditDate,Editor,Gerapporteerd,AantalFotos,fme_feature_type,arcgisfeatureservice_feature_url"
    ATTR_ACCUM_MODE = Only Use Result
    CLIP_TO_ENVELOPE = NO
    COMBINE_GEOM = Use Result
    FEATURETYPES = WSHD_DL_Dakonderhoud
    FORMAT = SAFE.ESRI-AGOL.ARCGISFEATURESERVICE
    GEOMETRY_TYPES = WSHD_DL_Dakonderhoud,""",fme_point"""
    INITIATOR_FIRST_OUTPUT = default
    INTERACT = NONE
    ORDER_RESULTS = No
    OUTPUT_ADD_SCHEMA_ATTRIBUTES = NO
    OUTPUT_FEATURES_DISPLAY = Schema and Data Features
    SAFE.ESRI-AGOL.ARCGISFEATURESERVICE_AGOL_AUTH_NC = Esri ArcGIS Online (gisadmin_GKB)
    SAFE.ESRI-AGOL.ARCGISFEATURESERVICE_ALIAS_MODE = NONE
    SAFE.ESRI-AGOL.ARCGISFEATURESERVICE_CREATE_FEATURE_TABLES_FROM_DATA = Yes
    SAFE.ESRI-AGOL.ARCGISFEATURESERVICE_FEATURES_PER_REQUEST = 1000
    SAFE.ESRI-AGOL.ARCGISFEATURESERVICE_FEATURE_SERVICE_WITH_ID = WSHD_DL_Dakonderhoud(1221ec2727914d979f1b4c52705c3af4)
    SAFE.ESRI-AGOL.ARCGISFEATURESERVICE_FOLDER_NAME = WSHD Assets
    SAFE.ESRI-AGOL.ARCGISFEATURESERVICE_QUERY_FEATURE_TYPES_FOR_MERGE_FILTERS = Yes
    SAFE.ESRI-AGOL.ARCGISFEATURESERVICE_RESOLVE_DOMAINS = NO
    SAFE.ESRI-AGOL.ARCGISFEATURESERVICE_SAFE.ESRI-AGOL.ARCGISFEATURESERVICE_EXPOSE_FORMAT_ATTRS = fme_feature_type,String(50) arcgisfeatureservice_feature_url,String
    SAFE.ESRI-AGOL.ARCGISFEATURESERVICE_SITE_SOURCE_TYPE = USER
    SAFE.ESRI-AGOL.ARCGISFEATURESERVICE_URL_TYPE = AGOL
    SAFE.ESRI-AGOL.ARCGISFEATURESERVICE_USE_SEARCH_ENVELOPE = NO
    SAFE.ESRI-AGOL.ARCGISFEATURESERVICE_VERIFY_HTTPS = WEB_CONN
    WSHD_DL_Dakonderhoud -> Junction

Bookmark: Filtering atrribute handling
AttributeCreator__Datum_milliseconds_to_seconds
    ATTR_TABLE:
      SET_TO Datum (real64) = @Evaluate(@Value(CreationDate)/1000)
      SET_TO Vandaag (varchar(200)) = @DateTimeFormat(@DateTimeNow(),%Y%m%d)
    -> DateTimeConverter
DateTimeConverter
    DATETIME_ATTR = Datum
    IN_FORMAT = %s$
    OUT_FORMAT = %Y%m%d
    PASSTHROUGH = NO
    REPAIR_INPUT = YES
    -> TestFilter_status
    -> FeatureMerger_2 [SUPPLIER]
Note: Inventarisaties gaan allemaal door en worden later gefilterd op rapportagestatus. Dat is om deurnummer te kunnen genereren op basis van de bestaande deuren.
TestFilter_status
    DEFAULT_VALUE = Inspecties
    PASSED_TEST_GROUP_OUTPUT = FIRST
    TEST_LIST = "BOOL_OP,OR,COMPOSITE_TEST,""""""1"""""",TEST_CLAUSE,TEST @Value(InspectieStatus) = Inventarisatie",Inventarisatie
    Inventarisatie -> Sorter_op_Datum_2
    Inspecties -> TestFilter_2
TestFilter_2
    DEFAULT_VALUE = Gerapporteerd
    PASSED_TEST_GROUP_OUTPUT = FIRST
    TEST_LIST:
      "BOOL_OP,OR,COMPOSITE_TEST,""""""1 OR 2"""""",TEST_CLAUSE,TEST @Value(Gerapporteerd) = Nee
      TEST @Value(Gerapporteerd) = Gewijzigd",@Value(Gerapporteerd) = Nee OR Gewijzigd
    @Value(Gerapporteerd) = Nee OR Gewijzigd -> TestFilter_InspectieType
TestFilter_InspectieType
    DEFAULT_VALUE = InspectieType = Inspectie
    PASSED_TEST_GROUP_OUTPUT = FIRST
    TEST_LIST = "BOOL_OP,OR,COMPOSITE_TEST,""""""1"""""",TEST_CLAUSE,TEST @Value(InspectieType) = Storing",InspectieType = Storing
    InspectieType = Storing -> AttributeCombiner_2
    InspectieType = Storing -> Sorter_op_Datum_3
    InspectieType = Inspectie -> Sorter_op_Datum
    InspectieType = Inspectie -> AttributeCombiner

Bookmark: Maak survey123 rapportage
Note: fc997fd1dc7d4ddc9daeb3db6519661a
AttributeCombiner_2
    ATTRS = globalid
    DELIM = ,
    DROP_EMPTY = No
    QUOT = Single
    -> AGOL_GetToken_gisadmin_2 [HTTPCaller_Input]
AGOL_GetToken_gisadmin_2
    Password =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
    User = gisadmin_GKB
    AttributeExposer_Output -> AttributeCreator_3
AttributeCreator_3
    ATTR_TABLE:
      SET_TO fsURL (varchar(106)) = https://services9.arcgis.com/CjT8oELYhF7fnj6q/arcgis/rest/services/WSHD_DL_DeurInspecties/FeatureServer/0
      SET_TO featureLayerURL (varchar(200)) = featureLayerUrl=@Value(fsURL)
      SET_TO f (varchar(6)) = f=json
      SET_TO outputFileName (varchar(200)) = WSHD_DeurInspectie_@Value(LocatieCode)_@Value(DeurNummer)_@Value(Datum)
      SET_TO queryParameters (varchar(200)) = queryParameters={"where": "globalID IN (@Value(globalid))"}
      SET_TO outputFormat (varchar(16)) = outputFormat=pdf
      SET_TO templateItemId (varchar(47)) = templateItemId=fc997fd1dc7d4ddc9daeb3db6519661a
      SET_TO surveyItemId (varchar(45)) = surveyItemId=5e820d3109eb4d998e5563a148418a93
      SET_TO portalURL (varchar(32)) = portalURL=https://www.arcgis.com
      SET_TO utcOffset (varchar(18)) = utcOffset=<pipe><pipe>+02:00
      SET_TO locale (varchar(11)) = locale=<pipe><pipe>en
      SET_TO token_param (varchar(200)) = token=@Value(token)
      SET_TO webmapItemId (varchar(200))
      SET_TO merge (varchar(7)) = merge=1
      SET_TO mergeFiles (varchar(8)) = none
      SET_TO packageFiles (varchar(5)) = true
      SET_TO outputReportName (varchar(200)) = outputReportName=WSHD_ServiceRapport_${LocatieType}_${LocatieNaam}_${DeurNummer}_@Value(Vandaag)
      SET_TO outputPackageName (varchar(200)) = outputPackageName=WSHD_ServiceRapporten_@Value(Vandaag)
    -> AttributeManager_11
AttributeManager_11
    -> CreateRequest_2
CreateRequest_2: StringConcatenator
    ACTION = Create New Attribute
    PARM_LINE = @Value(f)&@Value(featureLayerURL)&@Value(locale)&@Value(outputReportName)&@Value(outputPackageName)&@Value(outputFormat)&@Value(portalURL)&@Value(queryParameters)&@Value(surveyItemId)&@Value(templateItemId)&@Value(utcOffset)&@Value(token_param)
    VAL_ATTR = bodyRequest
    -> createReport_2
createReport_2: HTTPCaller
    CONNECTION_TIMEOUT_LENGTH = 60
    CONTENT_TYPE_LOOKUP = application/x-www-form-urlencoded
    ERROR_ATTR = _error
    FOLLOW_REDIRECTS = FOLLOW_WITH_ORIGINAL_METHOD
    HTTP_METHOD = POST
    MAX_HTTP_VERSION = HTTP_2
    MAX_TRANSFERS_IN_PROGRESS = 25
    REDIRECT_AUTH = ORIGINAL_DOMAIN_ONLY
    SAVE_FILE_LOOKUP = NO
    STATUS_CODE_ATTR = _http_status_code
    TARGET_ATTR = _JobInfo
    TARGET_ATTR_ENCODING = auto-detect
    TARGET_URL = https://survey123.arcgis.com/api/featureReport/createReport/submitJob
    TRANSFER_TIMEOUT_LENGTH = 90
    UPLOAD_BODY = @Value(bodyRequest)
    UPLOAD_TYPE = Specify Upload Body
    USE_COOKIES = No
    VERIFY_SSL_CERTIFICATES = Yes
    SAVE_FILE = Attribute
    UPLOAD_CONTENT_TYPE = URL Encoded (application/x-www-form-urlencoded)
    -> JSONFlattener_2
JSONFlattener_2
    ERROR_LIST_ATTR = _json_error
    JSON_DOCUMENT = @Value(_JobInfo)
    NEW_ATTRIBUTES = inputInfo.jobType inputInfo.parameters.featureLayerUrl inputInfo.parameters.mergeFiles inputInfo.parameters.outputFileName inputInfo.parameters.outputFormat inputInfo.parameters.packageFiles inputInfo.parameters.queryParameters.where inputInfo.parameters.surveyItemId inputInfo.parameters.templateItemId jobId jobStatus resultInfo.title submitted success
    READ_FROM_FILE = NO
    RECURSIVE_LOOKUP = YES
    RECURSIVE = Yes
    -> Testfilter_Success_2
    <REJECTED> -> FoutCreateReport_2
Testfilter_Success_2: TestFilter
    DEFAULT_VALUE = No
    PASSED_TEST_GROUP_OUTPUT = FIRST
    TEST_LIST = "BOOL_OP,OR,COMPOSITE_TEST,""""""1"""""",TEST_CLAUSE,TEST @Value(success) = Yes",Yes
    Yes -> AttributeCreator_4
    No -> Terminator_2
AttributeCreator_4
    ATTR_TABLE = SET_TO jobURL (varchar(200)) = https://survey123.arcgis.com/api/featureReport/jobs/@Value(jobId)?username=gisadmin_GKB&token=@Value(token)
    -> JobStatusLooper_2 [JobStatus_Input]
JobStatusLooper_2
    JOBURL = @Value(jobURL)
    JobSuccess -> Flat_JobStatus_2
    JobError -> Logger_2
Flat_JobStatus_2: JSONFlattener
    ERROR_LIST_ATTR = _json_error
    JSON_DOCUMENT = @Value(_JobStatus)
    NEW_ATTRIBUTES = resultInfo resultInfo.succeededObjectIds{} resultInfo.resultFiles{0}.name resultInfo.resultFiles{0}.url
    READ_FROM_FILE = NO
    RECURSIVE_LOOKUP = YES
    RECURSIVE = Yes
    -> Attribute_manager_2
    -> ListExploder_objectIds
Attribute_manager_2: AttributeManager
    ATTR_TABLE:
      RENAME_SET_VALUE resultInfo.resultFiles{0}.name > report_naam
      RENAME_SET_VALUE resultInfo.resultFiles{0}.url > report_url
    -> HTTPCaller_2
HTTPCaller_2
    CLIENT_CERTIFICATE_TYPE = NONE
    CONNECTION_TIMEOUT_LENGTH = 120
    ERROR_ATTR = _error
    FILE_PATH_ATTR = _response_file_path
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    OUTPUT_FILENAME = FME_CONDITIONAL:DEFAULT_VALUE'$(FME_SHAREDRESOURCE_TEMP)@Value(report_naam)'BOOL_OP;OR;COMPOSITE_TEST;1;TEST $(FME_OS) = Windows'$(FME_SHAREDRESOURCE_TEMP)\@Value(report_naam)'FME_NUM_CONDITIONS2___
    REDIRECT_AUTH = ORIGINAL_DOMAIN_ONLY
    RESPONSE_TYPE = File
    RETRY_FAILED_TRANSFERS = CONNECTION 429 500 501 502 503 504 505 506 507 508 509 510 511
    RETRY_INITIAL_BACKOFF = 500
    RETRY_MAX_RETRIES = 5
    STATUS_CODE_ATTR = _http_status_code
    TARGET_URL = @Value(report_url)
    TRANSFER_TIMEOUT_LENGTH = 300
    USE_COOKIES = No
    VERIFY_SSL_CERTIFICATES = No
    -> FeatureMerger_met_report_gegevens_2 [REQUESTOR]
Logger_2
    LOG_FEATURE = LOG_RECORD
    MAXCOORDS = 20
    MAXFEATS = 20
    MESSAGE = Feature is:
    SEVERITY = INFO
FoutCreateReport_2: Logger
    LOG_FEATURE = LOG_ONLY
    MAXCOORDS = 20
    MAXFEATS = 20
    MESSAGE = Feature is:
    SEVERITY = INFO
    LOGGED -> Terminator_2
Terminator_2
    MESSAGE = Translation Terminated

Bookmark: Maak tabel
Sorter_op_Datum_3
    SORT_PARM = Datum NATURAL ASCENDING
    SORTED -> DateTimeConverter_8
DateTimeConverter_8
    DATETIME_ATTR = Datum
    IN_FORMAT = %Y%m%d
    OUT_FORMAT = %d-%m-%Y
    PASSTHROUGH = NO
    REPAIR_INPUT = YES
    -> FeatureCounter_3
FeatureCounter_3
    FeatureCounterNewAttrParameter = _numfeatures
    GroupBox = NO
    -> AttributeExposer__numfeatures_3
AttributeExposer__numfeatures_3
    ATTR_TABLE = _numfeatures,int16
    -> AttributeCreator_Opmerking_3
AttributeCreator_Opmerking_3
    ATTR_TABLE = SET_TO Opmerking (varchar(200))
    -> StringConcatenator__tabel_gegevens_2
StringConcatenator__tabel_gegevens_2
    ACTION = Create New Attribute
    PARM_LINE = <tr><td>@Value(Datum)</td><td>@Value(LocatieType)</td><td>@Value(LocatieNaam)</td><td>@Value(DeurNummer)</td><td>@Value(DeurType)</td><td>@Value(Opmerking)</td></tr>
    VAL_ATTR = _result
    -> AttributeCombiner_tabel_gegevens_2
AttributeCombiner_tabel_gegevens_2
    ATTRS = _result
    DROP_EMPTY = No
    QUOT = None
    -> StringConcatenator_tabel_met_header_3
StringConcatenator_tabel_met_header_3
    ACTION = Create New Attribute
    PARM_LINE = <table border=\"1\"><thead><td>Inspectiedatum</td><td>Functie</td><td>Locatie</td><td>Deurnummer</td><td>Deurtype</td><td>Opmerking</td></thead><tbody>@Value(_result)</tbody></table>
    VAL_ATTR = _result
    -> FeatureMerger_met_report_gegevens_2 [SUPPLIER]
FeatureMerger_met_report_gegevens_2
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> DateTimeConverter_6
DateTimeConverter_6
    DATETIME_ATTR = Vandaag
    IN_FORMAT = %Y%m%d
    OUT_FORMAT = %d-%m-%Y
    PASSTHROUGH = NO
    REPAIR_INPUT = YES
    -> GKB_EmailGenerator_4

Bookmark: Maak en verstuur mail
GKB_EmailGenerator_4
    ATTACHMENT = @Value(_response_file_path)
    Body = <H3>Servicerapporten </H3> <br> Aan: $(WVB_EMAIL) <br><br>    Er zijn <font color=red>@Value(_numfeatures)</font> servicewerkzaamheden uitgevoerd <br><br>@Value(_result)
    Subject = Rapportage @Value(Vandaag) @Value(_numfeatures) servicerapporten @Value(ProjectCode)
    To = $(WVB_EMAIL)
    VERZAMEL_MAIL = YES

Bookmark: Maak survey123 rapportage inspecties
AttributeCombiner
    ATTRS = globalid
    DELIM = ,
    DROP_EMPTY = No
    QUOT = Single
    -> AGOL_GetToken_gisadmin [HTTPCaller_Input]
AGOL_GetToken_gisadmin
    Password =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
    User = gisadmin_GKB
    AttributeExposer_Output -> AttributeCreator
AttributeCreator
    ATTR_TABLE:
      SET_TO fsURL (varchar(106)) = https://services9.arcgis.com/CjT8oELYhF7fnj6q/arcgis/rest/services/WSHD_DL_DeurInspecties/FeatureServer/0
      SET_TO featureLayerURL (varchar(200)) = featureLayerUrl=@Value(fsURL)
      SET_TO f (varchar(6)) = f=json
      SET_TO outputFileName (varchar(200)) = WSHD_DeurInspectie_@Value(LocatieCode)_@Value(DeurNummer)_@Value(Datum)
      SET_TO queryParameters (varchar(200)) = queryParameters={"where": "globalID IN (@Value(globalid))"}
      SET_TO outputFormat (varchar(16)) = outputFormat=pdf
      SET_TO templateItemId (varchar(47)) = templateItemId=ad09d7b3094b4714a42f7ccb66b71ca2
      SET_TO surveyItemId (varchar(45)) = surveyItemId=5e820d3109eb4d998e5563a148418a93
      SET_TO portalURL (varchar(32)) = portalURL=https://www.arcgis.com
      SET_TO utcOffset (varchar(18)) = utcOffset=<pipe><pipe>+02:00
      SET_TO locale (varchar(11)) = locale=<pipe><pipe>en
      SET_TO token_param (varchar(200)) = token=@Value(token)
      SET_TO webmapItemId (varchar(200))
      SET_TO merge (varchar(7)) = merge=1
      SET_TO mergeFiles (varchar(8)) = none
      SET_TO packageFiles (varchar(5)) = true
      SET_TO outputReportName (varchar(200)) = outputReportName=WSHD_DeurInspectie_${LocatieType}_${LocatieNaam}_${DeurNummer}_@Value(Vandaag)
      SET_TO outputPackageName (varchar(200)) = outputPackageName=WSHD_DeurInspecties_@Value(Vandaag)
    -> AttributeManager
AttributeManager
    -> CreateRequest
CreateRequest: StringConcatenator
    ACTION = Create New Attribute
    PARM_LINE = @Value(f)&@Value(featureLayerURL)&@Value(locale)&@Value(outputReportName)&@Value(outputPackageName)&@Value(outputFormat)&@Value(portalURL)&@Value(queryParameters)&@Value(surveyItemId)&@Value(templateItemId)&@Value(utcOffset)&@Value(token_param)
    VAL_ATTR = bodyRequest
    -> createReport
createReport: HTTPCaller
    CONNECTION_TIMEOUT_LENGTH = 60
    CONTENT_TYPE_LOOKUP = application/x-www-form-urlencoded
    ERROR_ATTR = _error
    FOLLOW_REDIRECTS = FOLLOW_WITH_ORIGINAL_METHOD
    HTTP_METHOD = POST
    MAX_HTTP_VERSION = HTTP_2
    MAX_TRANSFERS_IN_PROGRESS = 25
    REDIRECT_AUTH = ORIGINAL_DOMAIN_ONLY
    SAVE_FILE_LOOKUP = NO
    STATUS_CODE_ATTR = _http_status_code
    TARGET_ATTR = _JobInfo
    TARGET_ATTR_ENCODING = auto-detect
    TARGET_URL = https://survey123.arcgis.com/api/featureReport/createReport/submitJob
    TRANSFER_TIMEOUT_LENGTH = 90
    UPLOAD_BODY = @Value(bodyRequest)
    UPLOAD_TYPE = Specify Upload Body
    USE_COOKIES = No
    VERIFY_SSL_CERTIFICATES = Yes
    SAVE_FILE = Attribute
    UPLOAD_CONTENT_TYPE = URL Encoded (application/x-www-form-urlencoded)
    -> JSONFlattener
JSONFlattener
    ERROR_LIST_ATTR = _json_error
    JSON_DOCUMENT = @Value(_JobInfo)
    NEW_ATTRIBUTES = inputInfo.jobType inputInfo.parameters.featureLayerUrl inputInfo.parameters.mergeFiles inputInfo.parameters.outputFileName inputInfo.parameters.outputFormat inputInfo.parameters.packageFiles inputInfo.parameters.queryParameters.where inputInfo.parameters.surveyItemId inputInfo.parameters.templateItemId jobId jobStatus resultInfo.title submitted success
    READ_FROM_FILE = NO
    RECURSIVE_LOOKUP = YES
    RECURSIVE = Yes
    -> Testfilter_Success
    <REJECTED> -> FoutCreateReport
Testfilter_Success: TestFilter
    DEFAULT_VALUE = No
    PASSED_TEST_GROUP_OUTPUT = FIRST
    TEST_LIST = "BOOL_OP,OR,COMPOSITE_TEST,""""""1"""""",TEST_CLAUSE,TEST @Value(success) = Yes",Yes
    Yes -> AttributeCreator_2
    No -> Terminator
AttributeCreator_2
    ATTR_TABLE = SET_TO jobURL (varchar(200)) = https://survey123.arcgis.com/api/featureReport/jobs/@Value(jobId)?username=gisadmin_GKB&token=@Value(token)
    -> JobStatusLooper [JobStatus_Input]
JobStatusLooper
    JOBURL = @Value(jobURL)
    JobSuccess -> Flat_JobStatus
    JobError -> Logger
Flat_JobStatus: JSONFlattener
    ERROR_LIST_ATTR = _json_error
    JSON_DOCUMENT = @Value(_JobStatus)
    NEW_ATTRIBUTES = resultInfo resultInfo.succeededObjectIds{} resultInfo.resultFiles{0}.name resultInfo.resultFiles{0}.url
    READ_FROM_FILE = NO
    RECURSIVE_LOOKUP = YES
    RECURSIVE = Yes
    -> Attribute_manager
    -> ListExploder_objectIds
Attribute_manager: AttributeManager
    ATTR_TABLE:
      RENAME_SET_VALUE resultInfo.resultFiles{0}.name > report_naam
      RENAME_SET_VALUE resultInfo.resultFiles{0}.url > report_url
    -> HTTPCaller
HTTPCaller
    CLIENT_CERTIFICATE_TYPE = NONE
    CONNECTION_TIMEOUT_LENGTH = 120
    ERROR_ATTR = _error
    FILE_PATH_ATTR = _response_file_path
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    OUTPUT_FILENAME = FME_CONDITIONAL:DEFAULT_VALUE'$(FME_SHAREDRESOURCE_TEMP)@Value(report_naam)'BOOL_OP;OR;COMPOSITE_TEST;1;TEST $(FME_OS) = Windows'$(FME_SHAREDRESOURCE_TEMP)\@Value(report_naam)'FME_NUM_CONDITIONS2___
    REDIRECT_AUTH = ORIGINAL_DOMAIN_ONLY
    RESPONSE_TYPE = File
    RETRY_FAILED_TRANSFERS = CONNECTION 429 500 501 502 503 504 505 506 507 508 509 510 511
    RETRY_INITIAL_BACKOFF = 500
    RETRY_MAX_RETRIES = 5
    STATUS_CODE_ATTR = _http_status_code
    TARGET_URL = @Value(report_url)
    TRANSFER_TIMEOUT_LENGTH = 300
    USE_COOKIES = No
    VERIFY_SSL_CERTIFICATES = No
    -> FeatureMerger_met_report_gegevens [REQUESTOR]
Logger
    LOG_FEATURE = LOG_RECORD
    MAXCOORDS = 20
    MAXFEATS = 20
    MESSAGE = Feature is:
    SEVERITY = INFO
FoutCreateReport: Logger
    LOG_FEATURE = LOG_ONLY
    MAXCOORDS = 20
    MAXFEATS = 20
    MESSAGE = Feature is:
    SEVERITY = INFO
    LOGGED -> Terminator
Terminator
    MESSAGE = Translation Terminated

Bookmark: Update rapportagestatus deurinspecties en overige velden
ListExploder_objectIds
    ATTR_CONFLICT_RES_LOOKUP = INCOMING_IF_CONFLICT
    INDEX_ATTR = _element_index
    LIST_ATTR = resultInfo.succeededObjectIds{}
    ATTR_ACCUM_MODE = Merge List Attributes
    ATTR_CONFLICT_RES = Use List Attribute Values
    ELEMENTS -> AttributeKeeper
AttributeKeeper
    CREATE_BULK_MODE_FEATURES = NO
    KEEP_ATTRS = resultInfo.succeededObjectIds
    -> FeatureMerger_2 [REQUESTOR]
FeatureMerger_2
    ATTR_ACCUM_MODE = Merge Supplier
    ATTR_CONFLICT_RES_LOOKUP = REQUESTOR_IF_CONFLICT
    IGNORE_NULLS = No
    JOIN_KEYS = @Value(resultInfo.succeededObjectIds) @Value(objectid) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeKeeper_2
AttributeKeeper_2
    CREATE_BULK_MODE_FEATURES = NO
    KEEP_ATTRS = Gerapporteerd,globalid,RapportageDatum
    -> AttributeManager_4
AttributeManager_4
    ATTR_TABLE:
      SET_TO Gerapporteerd (varchar(256)) = Ja
      SET_TO RapportageDatum (date) = @DateTimeNow()
    -> DateTimeConverter_naar_ARCGIS_format
DateTimeConverter_naar_ARCGIS_format
    DATETIME_ATTR = RapportageDatum
    OUT_FORMAT = %m/%d/%Y
    PASSTHROUGH = NO
    REPAIR_INPUT = YES
    -> WSHD_DL_Deurinspectie (writer SAFE.ESRI-AGOL.ARCGISFEATURESERVICE_1)

Bookmark: Maak tabel van inspecties
Sorter_op_Datum
    SORT_PARM = Datum NATURAL ASCENDING
    SORTED -> DateTimeConverter_3
DateTimeConverter_3
    DATETIME_ATTR = Datum
    IN_FORMAT = %Y%m%d
    OUT_FORMAT = %d-%m-%Y
    PASSTHROUGH = NO
    REPAIR_INPUT = YES
    -> TestFilter
TestFilter
    DEFAULT_VALUE = Geen QRDeur
    PASSED_TEST_GROUP_OUTPUT = FIRST
    TEST_LIST = "BOOL_OP,OR,COMPOSITE_TEST,""""""1"""""",TEST_CLAUSE,TEST QRDeur ATTRIBUTE_HAS_A_VALUE """,QRDeur heeft waarde
    QRDeur heeft waarde -> JSONExtractor_QRDeurType
    Geen QRDeur -> AttributeManager_3
JSONExtractor_QRDeurType
    EXTRACT_QUERY_TABLE = QRDeurType json["DeurType"]
    JSON_DOCUMENT = @Value(QRDeur)
    READ_FROM_FILE = NO
    EVALUATED -> FeatureCounter
AttributeManager_3
    ATTR_TABLE = SET_TO QRDeur (varchar(255)) = @Value(DeurType)
    -> FeatureCounter
FeatureCounter
    FeatureCounterNewAttrParameter = _numfeatures
    GroupBox = NO
    -> AttributeExposer__numfeatures
AttributeExposer__numfeatures
    ATTR_TABLE = _numfeatures,int16
    -> StringReplacer
StringReplacer
    CASE = NO
    FIND_TEXT = "\n"
    NO_MATCH = _FME_NO_OP_
    REGEXP = NO
    REPLACE_TEXT = " "
    SRC_ATTRS = Bijzonderheden
    -> AttributeCreator_Opmerking_4
Note: Check status QRCode en vastgelegde DeurType
AttributeCreator_Opmerking_4
    ATTR_TABLE:
      SET_TO Opmerking (varchar(200)) = FME_CONDITIONAL:DEFAULT_VALUE'@Value(Bijzonderheden)'BOOL_OP;AND;COMPOSITE_TEST;1 AND 2;TEST @Value(StatusQRCode) = Nee;TEST @Value(DeurNummer) = -1'@Value(Bijzonderheden) <font color=red>Deur zonder QR Code !! Laat QR Code aanmaken en plaatsen !!.</font>'BOOL_OP;COMPOSITE;COMPOSITE_TEST;1 AND 2;TEST @Value(DeurType) != @Value(QRDeurType);TEST @Value(DeurNummer) = -1'@Value(Bijzonderheden) <font color=#ff4500>Deurtype gewijzigd !! Laat QR Code vernieuwen  en plaatsen !!.</font>'FME_NUM_CONDITIONS3___
      SET_TO Uitslag (varchar(200)) = FME_CONDITIONAL:DEFAULT_VALUE'<font color=green>Goedgekeurd !!</font>'BOOL_OP;OR;COMPOSITE_TEST;1;TEST @Value(DeurGoedgekeurd) = Nee'<font color=red>Afgekeurd !!</font>'FME_NUM_CONDITIONS2___
    -> StringConcatenator__tabel_gegevens
StringConcatenator__tabel_gegevens
    ACTION = Create New Attribute
    PARM_LINE = <tr><td>@Value(Datum)</td><td>@Value(LocatieType)</td><td>@Value(LocatieNaam)</td><td>@Value(DeurNummer)</td><td>@Value(DeurType)</td><td>@Value(Uitslag)</td><td>@Value(Opmerking)</td></tr>
    VAL_ATTR = _result
    -> AttributeCombiner_tabel_gegevens
AttributeCombiner_tabel_gegevens
    ATTRS = _result
    DROP_EMPTY = No
    QUOT = None
    -> StringConcatenator_tabel_met_header
StringConcatenator_tabel_met_header
    ACTION = Create New Attribute
    PARM_LINE = <table border=\"1\"><thead><td>Inspectiedatum</td><td>Functie</td><td>Locatie</td><td>Deurnummer</td><td>Deurtype</td><td>Uitslag</td><td>Opmerking</td></thead><tbody>@Value(_result)</tbody></table>
    VAL_ATTR = _result
    -> FeatureMerger_met_report_gegevens [SUPPLIER]
FeatureMerger_met_report_gegevens
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> DateTimeConverter_2
DateTimeConverter_2
    DATETIME_ATTR = Vandaag
    IN_FORMAT = %Y%m%d
    OUT_FORMAT = %d-%m-%Y
    PASSTHROUGH = NO
    REPAIR_INPUT = YES
    -> GKB_EmailGenerator_5

Bookmark: Maak en verstuur mail
GKB_EmailGenerator_5
    ATTACHMENT = @Value(_response_file_path)
    Body = <H3>Rapportage deurinspecties </H3> <br> Aan: $(WVB_EMAIL) <br><br>    Er zijn <font color=red>@Value(_numfeatures)</font> nieuwe inspecties uitgevoerd <br><br>@Value(_result)
    CC = melanie@hoeksedeurenservice.nl,dirkjan@gkbgroep.nl
    Subject = Rapportage @Value(Vandaag) @Value(_numfeatures) deurinspecties @Value(ProjectCode)
    To = $(WVB_EMAIL)
    VERZAMEL_MAIL = YES

Bookmark: Maak tabel van inventarisaties
Sorter_op_Datum_2
    SORT_PARM = Datum NATURAL ASCENDING
    SORTED -> DateTimeConverter_4
DateTimeConverter_4
    DATETIME_ATTR = Datum
    IN_FORMAT = %Y%m%d
    OUT_FORMAT = %d-%m-%Y
    PASSTHROUGH = NO
    REPAIR_INPUT = YES
    -> TestFilter_3
FeatureMerger_met_nieuwe_gegevens
    ATTR_ACCUM_MODE = Merge Supplier
    ATTR_CONFLICT_RES_LOOKUP = SUPPLIER_IF_CONFLICT
    IGNORE_NULLS = No
    JOIN_KEYS = @Value(globalid) @Value(globalid) AUTO
    MERGE_TYPE_VAL = ATTRIBUTES
    PROCESS_DUPS = NO
    REJECT_NULL_MISSING_KEYS = No
    SUPPLIERS_FIRST = No
    ATTR_CONFLICT_RES = Use Supplier
    MERGE_TYPE = Attributes Only
    MERGED -> TestFilter_6
    UNMERGED_REQUESTOR -> TestFilter_6
TestFilter_6
    DEFAULT_VALUE = Gerapporteerd
    PASSED_TEST_GROUP_OUTPUT = FIRST
    TEST_LIST:
      "BOOL_OP,OR,COMPOSITE_TEST,""""""1 OR 2"""""",TEST_CLAUSE,TEST @Value(Gerapporteerd) = Nee
      TEST @Value(Gerapporteerd) = Gewijzigd",@Value(Gerapporteerd) = Nee OR Gewijzigd
    @Value(Gerapporteerd) = Nee OR Gewijzigd -> FeatureCounter_2
FeatureCounter_2
    FeatureCounterNewAttrParameter = _numfeatures
    GroupBox = NO
    -> AttributeExposer__numfeatures_2
AttributeExposer__numfeatures_2
    ATTR_TABLE = _numfeatures,int16
    -> StringReplacer_2
StringReplacer_2
    CASE = NO
    FIND_TEXT = "\n"
    NO_MATCH = _FME_NO_OP_
    REGEXP = NO
    REPLACE_TEXT = " "
    SRC_ATTRS = Herzien
    -> AttributeCreator_Opmerking_2
AttributeCreator_Opmerking_2
    ATTR_TABLE = SET_TO Opmerking (varchar(200)) = <font color=red>@Value(Herzien).</font>
    -> StringConcatenator_tabeldata
StringConcatenator_tabeldata
    ACTION = Create New Attribute
    PARM_LINE = <tr><td>@Value(Datum)</td><td>@Value(LocatieType)</td><td>@Value(LocatieNaam)</td><td>@Value(DeurNummer)</td><td>@Value(DeurType)</td><td>@Value(Opmerking)</td></tr>
    VAL_ATTR = _result
    -> AttributeKeeper_voor_UPDATe_AGOL
    -> AttributeCombiner_tabledata
AttributeKeeper_voor_UPDATe_AGOL
    CREATE_BULK_MODE_FEATURES = NO
    KEEP_ATTRS = Gerapporteerd,RapportageDatum,globalid,DeurNummer,Herzien,QRDeur
    -> AttributeManager_4
AttributeCombiner_tabledata
    ATTRS = _result
    DROP_EMPTY = No
    QUOT = None
    -> StringConcatenator_tabel_met_header_2
StringConcatenator_tabel_met_header_2
    ACTION = Create New Attribute
    PARM_LINE = <table border=\"1\"><thead><td>Inventaristiedatum</td><td>Functie</td><td>Locatie</td><td>Deurnummer</td><td>Deurtype</td><td>Opmerking</td></thead><tbody>@Value(_result)</tbody></table>
    VAL_ATTR = _result
    -> DateTimeConverter_5
DateTimeConverter_5
    DATETIME_ATTR = Vandaag
    IN_FORMAT = %Y%m%d
    OUT_FORMAT = %d-%m-%Y
    PASSTHROUGH = NO
    REPAIR_INPUT = YES
    -> GKB_EmailGenerator_3

Bookmark: Check DeurType
TestFilter_3
    DEFAULT_VALUE = Geen QRDeur
    PASSED_TEST_GROUP_OUTPUT = FIRST
    TEST_LIST = "BOOL_OP,OR,COMPOSITE_TEST,""""""1"""""",TEST_CLAUSE,TEST QRDeur ATTRIBUTE_HAS_A_VALUE """,QRDeur heeft waarde
    QRDeur heeft waarde -> JSONExtractor_QRDeurType_2
    Geen QRDeur -> AttributeManager_5
JSONExtractor_QRDeurType_2
    EXTRACT_QUERY_TABLE = QRDeurType json["DeurType"]
    JSON_DOCUMENT = @Value(QRDeur)
    READ_FROM_FILE = NO
    EVALUATED -> AttributeValueMapper_DeurType
    EVALUATED -> FeatureMerger_met_nieuwe_gegevens [REQUESTOR]
AttributeManager_5
    ATTR_TABLE = SET_TO QRDeur (varchar(255)) = @Value(DeurType)
    -> AttributeValueMapper_DeurType
    -> FeatureMerger_met_nieuwe_gegevens [REQUESTOR]

Bookmark: Deurnummer en QR maken
AttributeValueMapper_DeurType
    LUT = Roldeur,RD,Overheaddeur,OD,Snelloopdeur,LD,Brandrolluik,BR,Vouwdeur,VD
    MAPPING_DIRECTION = FORWARD
    SRC = DeurType
    VAL_ATTR = Prefix
    -> TestFilter_7
TestFilter_7
    DEFAULT_VALUE = Geen actie
    PASSED_TEST_GROUP_OUTPUT = FIRST
    TEST_LIST = "BOOL_OP,OR,COMPOSITE_TEST,""""""1"""""",TEST_CLAUSE,TEST @Value(StatusQRCode) = Nee",Geen QR Code,"BOOL_OP,OR,COMPOSITE_TEST,""""""1"""""",TEST_CLAUSE,TEST @Value(DeurType) != @Value(QRDeurType)",Deurtype verschil
    Geen QR Code -> AttributeCreator_6
    Deurtype verschil -> AttributeCreator_6
    Geen actie -> AttributeSplitter_DeurNummer
AttributeCreator_6
    ATTR_TABLE = SET_TO CodeDeurType (varchar(200)) = @Value(Prefix)
    -> Counter_2
Counter_2
    CNT_ATTR = _count
    GROUP_BY = DeurType LocatieCode
    SCOPE = Local
    START = 1
    -> FeatureMerger_5 [REQUESTOR]
AttributeSplitter_DeurNummer
    ATTR_NAME = DeurNummer
    DELIMITER = -
    DROP_EMPTY_PARTS = NO
    LIST_NAME = _list
    TRIM_TYPE = BOTH
    -> AttributeCreator_5
AttributeCreator_5
    ATTR_TABLE:
      SET_TO CodeDeurType (varchar(200)) = @Value(Prefix)
      SET_TO VolgnummerDeur (varchar(200)) = @Value(_list{1})
    -> StatisticsCalculator_3
StatisticsCalculator_3
    ATTR_ACCUM_MODE = None
    CALCULATION_MODE = NUMERIC
    FEAT_STATS = VolgnummerDeur,NUMERIC_MODE,,MAX,COUNT,,,,,,,,,,
    GROUP_BY = CodeDeurType LocatieCode
    SUMMARY -> FeatureMerger_5 [SUPPLIER]
FeatureMerger_5
    ATTR_ACCUM_MODE = Merge Supplier
    ATTR_CONFLICT_RES_LOOKUP = REQUESTOR_IF_CONFLICT
    IGNORE_NULLS = No
    JOIN_KEYS = @Value(LocatieCode) @Value(LocatieCode) AUTO @Value(CodeDeurType) @Value(CodeDeurType) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeManager_12
    UNMERGED_REQUESTOR -> AttributeManager_12
AttributeManager_12
    ATTR_TABLE:
      SET_TO VolgnummerDeur.max (real64) = FME_CONDITIONAL:DEFAULT_VALUE'_FME_NO_OP_'BOOL_OP;OR;COMPOSITE_TEST;1;TEST VolgnummerDeur.max ATTRIBUTE_IS_MISSING _FME_BLANK_STRING_'0'FME_NUM_CONDITIONS2___
      SET_TO DeurNummerOud (varchar(200)) = @Value(DeurNummer)
      SET_TO DeurNummer (varchar(255)) = @Value(CodeDeurType)-@Format(%03d,@sum(@Value(VolgnummerDeur.max),@Value(_count)))
      SET_TO Herzien (varchar(50)) = QR Code Herzien (@Value(DeurNummerOud))
    -> StringConcatenator_QRDeur
StringConcatenator_QRDeur
    ACTION = Create New Attribute
    PARM_LINE = {"LocatieType": "@Value(LocatieType)","LocatieCode": "@Value(LocatieCode)","LocatieNaam": "@Value(LocatieNaam)","DeurNummer": "@Value(DeurNummer)","DeurType": "@Value(DeurType)"}
    VAL_ATTR = QRDeur
    -> AttributeKeeper_5
AttributeKeeper_5
    CREATE_BULK_MODE_FEATURES = NO
    KEEP_ATTRS = DeurNummer,Herzien,globalid,QRDeur
    -> FeatureMerger_met_nieuwe_gegevens [SUPPLIER]

Bookmark: Updates
WSHD_DL_Deurinspectie (writer SAFE.ESRI-AGOL.ARCGISFEATURESERVICE_1)
    attributes: globalid GlobalID(38), Gerapporteerd String(256), RapportageDatum String(254), QRDeur String(254), Herzien String(50), DeurNummer String(254)
WSHD_DL_OnderhoudsLocaties (writer SAFE.ESRI-AGOL.ARCGISFEATURESERVICE_6)
    attributes: AantalDeuren SmallInteger, GlobalID GlobalID(38), InspectieStatus String(256), AantalDeurinspectiesDitJaar Integer, StatusDakonderhoud String(255)
WSHD_DL_Dakonderhoud (writer SAFE.ESRI-AGOL.ARCGISFEATURESERVICE_7)
    attributes: Gerapporteerd String(256), RapportageDatum String(254), GlobalID String(38)

Bookmark: Maak en verstuur mail
GKB_EmailGenerator_3
    Body = <H3>Rapportage deurinventarisaties </H3> <br> Aan: $(WVB_EMAIL) <br><br>    Er zijn <font color=red>@Value(_numfeatures)</font> nieuwe QR codes geplaatst / inventarisaties gemaakt <br><br>@Value(_result)
    CC = dirkjan@gkbgroep.nl
    Subject = Rapportage @Value(Vandaag) @Value(_numfeatures) deuren geïnventariseerd @Value(ProjectCode)
    To = $(WVB_EMAIL)
    VERZAMEL_MAIL = YES

Bookmark: Aantal geïnventariseerde deuren per locatie per jaar en status locatie updaten
AttributeCreator__Datum_milliseconds_to_seconds_2
    ATTR_TABLE:
      SET_TO Datum (real64) = @Evaluate(@Value(CreationDate)/1000)
      SET_TO JaarVandaag (varchar(200)) = @DateTimeNow()
    -> TestFilter_4
TestFilter_4
    DEFAULT_VALUE = <UNFILTERED>
    PASSED_TEST_GROUP_OUTPUT = FIRST
    TEST_LIST = "BOOL_OP,OR,COMPOSITE_TEST,""""""1"""""",TEST_CLAUSE,TEST @Value(InspectieType) = Inspectie",Ge:inspecteerde deuren,"BOOL_OP,OR,COMPOSITE_TEST,""""""1"""""",TEST_CLAUSE,TEST @Value(InspectieType) = Inventarisatie",Geinventariseerde deuren
    Ge:inspecteerde deuren -> DateTimeConverter_7
    Geinventariseerde deuren -> StatisticsCalculator
StatisticsCalculator
    ATTR_ACCUM_MODE = None
    CALCULATION_MODE = NUMERIC
    FEAT_STATS = globalid,NUMERIC_MODE,,,COUNT,,,,,,,,,,
    GROUP_BY = LocatieCode
    SUMMARY -> AttributeManager_7
AttributeManager_7
    ATTR_TABLE = RENAME_SET_VALUE globalid.total_count > AantalDeuren (uint64)
    -> FeatureMerger [REQUESTOR]
DateTimeConverter_7
    DATETIME_ATTR = JaarVandaag
    OUT_FORMAT = %Y
    PASSTHROUGH = NO
    REPAIR_INPUT = YES
    -> TestFilter_dit_jaar
TestFilter_dit_jaar
    DEFAULT_VALUE = <UNFILTERED>
    PASSED_TEST_GROUP_OUTPUT = FIRST
    TEST_LIST = "BOOL_OP,OR,COMPOSITE_TEST,""""""1"""""",TEST_CLAUSE,TEST @Value(InspectieJaar) = @Value(JaarVandaag)",Inspecties dit jaar
    Inspecties dit jaar -> StatisticsCalculator_2
StatisticsCalculator_2
    ATTR_ACCUM_MODE = None
    CALCULATION_MODE = NUMERIC
    FEAT_STATS = globalid,NUMERIC_MODE,,,COUNT,,,,,,,,,,
    GROUP_BY = LocatieCode
    SUMMARY -> AttributeManager_9
AttributeManager_9
    ATTR_TABLE = RENAME_SET_VALUE globalid.total_count > AantalDeurinspectiesDitJaar (uint64) = FME_CONDITIONAL:DEFAULT_VALUE'_FME_NO_OP_'BOOL_OP;OR;COMPOSITE_TEST;1;TEST @Value(AantalDeurinspectiesDitJaar) NOT_> 0'0'FME_NUM_CONDITIONS2___
    -> FeatureMerger [SUPPLIER]
FeatureMerger
    ATTR_ACCUM_MODE = Merge Supplier
    ATTR_CONFLICT_RES_LOOKUP = REQUESTOR_IF_CONFLICT
    IGNORE_NULLS = No
    JOIN_KEYS = @Value(LocatieCode) @Value(LocatieCode) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeManager_10
    UNMERGED_REQUESTOR -> AttributeManager_10
AttributeManager_10
    ATTR_TABLE = SET_TO AantalDeurinspectiesDitJaar (uint64) = FME_CONDITIONAL:DEFAULT_VALUE'_FME_NO_OP_'BOOL_OP;OR;COMPOSITE_TEST;1 OR 2;TEST @Value(AantalDeurinspectiesDitJaar) NOT_> 0;TEST AantalDeurinspectiesDitJaar ATTRIBUTE_IS_MISSING _FME_BLANK_STRING_'0'FME_NUM_CONDITIONS2___
    USER_EXPOSED_ATTRIBUTES = globalid.total_count
    -> FeatureMerger_3 [SUPPLIER]
FeatureMerger_3
    ATTR_ACCUM_MODE = Merge Supplier
    ATTR_CONFLICT_RES_LOOKUP = SUPPLIER_IF_CONFLICT
    IGNORE_NULLS = No
    JOIN_KEYS = @Value(Code) @Value(LocatieCode) AUTO
    MERGE_TYPE_VAL = ATTRIBUTES
    PROCESS_DUPS = NO
    REJECT_NULL_MISSING_KEYS = No
    SUPPLIERS_FIRST = No
    ATTR_CONFLICT_RES = Use Supplier
    MERGE_TYPE = Attributes Only
    MERGED -> AttributeManager_6
    UNMERGED_REQUESTOR -> AttributeManager_8
AttributeManager_6
    ATTR_TABLE = SET_TO InspectieStatus (varchar(256)) = FME_CONDITIONAL:DEFAULT_VALUE'_FME_NO_OP_'BOOL_OP;OR;COMPOSITE_TEST;1;TEST @Value(AantalDeuren) = @Value(AantalDeurinspectiesDitJaar)'Gereed'BOOL_OP;AND;COMPOSITE_TEST;1 AND 2;TEST @Value(AantalDeuren) > @Value(AantalDeurinspectiesDitJaar);TEST @Value(InspectieStatus) = Gereed'Uitvoeren'FME_NUM_CONDITIONS3___
    -> AttributeKeeper_4
AttributeManager_8
    ATTR_TABLE:
      SET_TO AantalDeuren (int16) = 0
      SET_TO AantalDeurinspectiesDitJaar (int32) = 0
    -> AttributeKeeper_4
AttributeKeeper_4
    CREATE_BULK_MODE_FEATURES = NO
    KEEP_ATTRS = AantalDeuren,GlobalID,AantalDeurinspectiesDitJaar,InspectieStatus
    -> WSHD_DL_OnderhoudsLocaties (writer SAFE.ESRI-AGOL.ARCGISFEATURESERVICE_6)

Bookmark: Maak tabel
Sorter_op_Datum_4
    SORT_PARM = Datum NATURAL ASCENDING
    SORTED -> DateTimeConverter_10
DateTimeConverter_10
    DATETIME_ATTR = Datum
    IN_FORMAT = %Y%m%d
    OUT_FORMAT = %d-%m-%Y
    PASSTHROUGH = NO
    REPAIR_INPUT = YES
    -> FeatureCounter_4
FeatureCounter_4
    FeatureCounterNewAttrParameter = _numfeatures
    GroupBox = NO
    -> StringReplacer_3
StringReplacer_3
    CASE = NO
    FIND_TEXT = "\n"
    NO_MATCH = _FME_NO_OP_
    REGEXP = NO
    REPLACE_TEXT = " "
    SRC_ATTRS = Bijzonderheden,OmschrijvingExtraWerkzaamheden
    -> AttributeExposer__numfeatures_4
AttributeExposer__numfeatures_4
    ATTR_TABLE = _numfeatures,int16
    -> AttributeCreator_Opmerking_5
AttributeCreator_Opmerking_5
    ATTR_TABLE:
      SET_TO Opmerking (varchar(200)) = FME_CONDITIONAL:DEFAULT_VALUE'@Value(Bijzonderheden)'BOOL_OP;OR;COMPOSITE_TEST;1;TEST @Value(ExtraWerkzaamheden) = Ja'@Value(Bijzonderheden)<br>Opvolgactie: @Value(OmschrijvingExtraWerkzaamheden)'FME_NUM_CONDITIONS2___
      SET_TO StatusKleur (varchar(200)) = FME_CONDITIONAL:DEFAULT_VALUE'Blue'BOOL_OP;OR;COMPOSITE_TEST;1;TEST @Value(StatusDakonderhoud) = Gereed'Green'BOOL_OP;OR;COMPOSITE_TEST;1;TEST @Value(StatusDakonderhoud) = Niet uitvoerbaar'Red'BOOL_OP;OR;COMPOSITE_TEST;1;TEST @Value(StatusDakonderhoud) = Deels'Orange'FME_NUM_CONDITIONS4___
    -> StringConcatenator__tabel_gegevens_3
StringConcatenator__tabel_gegevens_3
    ACTION = Create New Attribute
    PARM_LINE = <tr><td>@Value(Datum)</td><td>@Value(LocatieType)</td><td>@Value(LocatieNaam)</td><td><font color=@Value(StatusKleur)>@Value(StatusDakonderhoud)</font></td><td>@Value(ExtraWerkzaamheden)</td><td>@Value(AantalFotos)</td><td>@Value(Opmerking)</td></tr>
    VAL_ATTR = _result
    -> AttributeCombiner_tabel_gegevens_3
AttributeCombiner_tabel_gegevens_3
    ATTRS = _result
    DROP_EMPTY = No
    QUOT = None
    -> StringConcatenator_tabel_met_header_4
StringConcatenator_tabel_met_header_4
    ACTION = Create New Attribute
    PARM_LINE = <table border=\"1\"><thead><td>Inspectiedatum</td><td>Functie</td><td>Locatie</td><td>Status</td><td>Opvolgactie</td><td>Aantal fotos</td><td>Bijzonderheden</td></thead><tbody>@Value(_result)</tbody></table>
    VAL_ATTR = _result
    -> FeatureMerger_met_report_gegevens_3 [SUPPLIER]
FeatureMerger_met_report_gegevens_3
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> DateTimeConverter_9
DateTimeConverter_9
    DATETIME_ATTR = Vandaag
    IN_FORMAT = %Y%m%d
    OUT_FORMAT = %d-%m-%Y
    PASSTHROUGH = NO
    REPAIR_INPUT = YES
    -> GKB_EmailGenerator_2
    -> GKB_EmailGenerator_6
GKB_EmailGenerator_6 [off]
    Body = <H3>Rapportage dakonderhoud </H3> <br> Aan: $(WVB_EMAIL) <br><br>    Er zijn voor <font color=red>@Value(_numfeatures)</font> locaties meldingen voor dakonderhoud gedaan <br><br>@Value(_result)
    Subject = Rapportage @Value(Vandaag) @Value(_numfeatures) meldingen dakonderhoud @Value(ProjectCode)
    To = $(WVB_EMAIL)
    VERZAMEL_MAIL = YES

Bookmark: Maak survey123 rapportage
Note: fc997fd1dc7d4ddc9daeb3db6519661a
AttributeCombiner_3
    ATTRS = GlobalID
    DELIM = ,
    DROP_EMPTY = No
    QUOT = Single
    -> AGOL_GetToken_gisadmin_3 [HTTPCaller_Input]
AGOL_GetToken_gisadmin_3
    Password =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
    User = gisadmin_GKB
    AttributeExposer_Output -> AttributeCreator_7
AttributeCreator_7
    ATTR_TABLE:
      SET_TO fsURL (varchar(106)) = https://services9.arcgis.com/CjT8oELYhF7fnj6q/arcgis/rest/services/WSHD_DL_Dakonderhoud/FeatureServer/0
      SET_TO featureLayerURL (varchar(200)) = featureLayerUrl=@Value(fsURL)
      SET_TO f (varchar(6)) = f=json
      SET_TO outputFileName (varchar(200)) = WSHD_Dakonderhoud_@Value(LocatieCode)_@Value(Datum)
      SET_TO queryParameters (varchar(200)) = queryParameters={"where": "GlobalID IN (@Value(GlobalID))"}
      SET_TO outputFormat (varchar(16)) = outputFormat=pdf
      SET_TO templateItemId (varchar(47)) = templateItemId=10b1cc491520463aa97d676f4f9fab4f
      SET_TO surveyItemId (varchar(45)) = surveyItemId=9949f70d1c184b80aa0a63b2197b9d9b
      SET_TO portalURL (varchar(32)) = portalURL=https://www.arcgis.com
      SET_TO utcOffset (varchar(18)) = utcOffset=<pipe><pipe>+02:00
      SET_TO locale (varchar(11)) = locale=<pipe><pipe>en
      SET_TO token_param (varchar(200)) = token=@Value(token)
      SET_TO webmapItemId (varchar(200))
      SET_TO merge (varchar(7)) = merge=1
      SET_TO mergeFiles (varchar(8)) = none
      SET_TO packageFiles (varchar(5)) = true
      SET_TO outputReportName (varchar(200)) = outputReportName=WSHD_Dakonderhoud_${LocatieType}_${LocatieNaam}_@Value(Vandaag)
      SET_TO outputPackageName (varchar(200)) = outputPackageName=WSHD_Dakonderhoud_rapportages_@Value(Vandaag)
    -> AttributeManager_15
AttributeManager_15
    -> CreateRequest_4
CreateRequest_4: StringConcatenator
    ACTION = Create New Attribute
    PARM_LINE = @Value(f)&@Value(featureLayerURL)&@Value(locale)&@Value(outputReportName)&@Value(outputPackageName)&@Value(outputFormat)&@Value(portalURL)&@Value(queryParameters)&@Value(surveyItemId)&@Value(templateItemId)&@Value(utcOffset)&@Value(token_param)
    VAL_ATTR = bodyRequest
    -> createReport_3
createReport_3: HTTPCaller
    CONNECTION_TIMEOUT_LENGTH = 60
    CONTENT_TYPE_LOOKUP = application/x-www-form-urlencoded
    ERROR_ATTR = _error
    FOLLOW_REDIRECTS = FOLLOW_WITH_ORIGINAL_METHOD
    HTTP_METHOD = POST
    MAX_HTTP_VERSION = HTTP_2
    MAX_TRANSFERS_IN_PROGRESS = 25
    REDIRECT_AUTH = ORIGINAL_DOMAIN_ONLY
    SAVE_FILE_LOOKUP = NO
    STATUS_CODE_ATTR = _http_status_code
    TARGET_ATTR = _JobInfo
    TARGET_ATTR_ENCODING = auto-detect
    TARGET_URL = https://survey123.arcgis.com/api/featureReport/createReport/submitJob
    TRANSFER_TIMEOUT_LENGTH = 90
    UPLOAD_BODY = @Value(bodyRequest)
    UPLOAD_TYPE = Specify Upload Body
    USE_COOKIES = No
    VERIFY_SSL_CERTIFICATES = Yes
    SAVE_FILE = Attribute
    UPLOAD_CONTENT_TYPE = URL Encoded (application/x-www-form-urlencoded)
    -> JSONFlattener_3
JSONFlattener_3
    ERROR_LIST_ATTR = _json_error
    JSON_DOCUMENT = @Value(_JobInfo)
    NEW_ATTRIBUTES = inputInfo.jobType inputInfo.parameters.featureLayerUrl inputInfo.parameters.mergeFiles inputInfo.parameters.outputFileName inputInfo.parameters.outputFormat inputInfo.parameters.packageFiles inputInfo.parameters.queryParameters.where inputInfo.parameters.surveyItemId inputInfo.parameters.templateItemId jobId jobStatus resultInfo.title submitted success
    READ_FROM_FILE = NO
    RECURSIVE_LOOKUP = YES
    RECURSIVE = Yes
    -> Testfilter_Success_3
    <REJECTED> -> FoutCreateReport_3
Testfilter_Success_3: TestFilter
    DEFAULT_VALUE = No
    PASSED_TEST_GROUP_OUTPUT = FIRST
    TEST_LIST = "BOOL_OP,OR,COMPOSITE_TEST,""""""1"""""",TEST_CLAUSE,TEST @Value(success) = Yes",Yes
    Yes -> AttributeCreator_8
    No -> Terminator_3
AttributeCreator_8
    ATTR_TABLE = SET_TO jobURL (varchar(200)) = https://survey123.arcgis.com/api/featureReport/jobs/@Value(jobId)?username=gisadmin_GKB&token=@Value(token)
    -> JobStatusLooper_3 [JobStatus_Input]
JobStatusLooper_3
    JOBURL = @Value(jobURL)
    JobSuccess -> Flat_JobStatus_3
    JobError -> Logger_3
Flat_JobStatus_3: JSONFlattener
    ERROR_LIST_ATTR = _json_error
    JSON_DOCUMENT = @Value(_JobStatus)
    NEW_ATTRIBUTES = resultInfo resultInfo.succeededObjectIds{} resultInfo.resultFiles{0}.name resultInfo.resultFiles{0}.url
    READ_FROM_FILE = NO
    RECURSIVE_LOOKUP = YES
    RECURSIVE = Yes
    -> Attribute_manager_3
Attribute_manager_3: AttributeManager
    ATTR_TABLE:
      RENAME_SET_VALUE resultInfo.resultFiles{0}.name > report_naam
      RENAME_SET_VALUE resultInfo.resultFiles{0}.url > report_url
    -> HTTPCaller_3
HTTPCaller_3
    CLIENT_CERTIFICATE_TYPE = NONE
    CONNECTION_TIMEOUT_LENGTH = 120
    ERROR_ATTR = _error
    FILE_PATH_ATTR = _response_file_path
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    OUTPUT_FILENAME = FME_CONDITIONAL:DEFAULT_VALUE'$(FME_SHAREDRESOURCE_TEMP)@Value(report_naam)'BOOL_OP;OR;COMPOSITE_TEST;1;TEST $(FME_OS) = Windows'$(FME_SHAREDRESOURCE_TEMP)\@Value(report_naam)'FME_NUM_CONDITIONS2___
    REDIRECT_AUTH = ORIGINAL_DOMAIN_ONLY
    RESPONSE_TYPE = File
    RETRY_FAILED_TRANSFERS = CONNECTION 429 500 501 502 503 504 505 506 507 508 509 510 511
    RETRY_INITIAL_BACKOFF = 500
    RETRY_MAX_RETRIES = 5
    STATUS_CODE_ATTR = _http_status_code
    TARGET_URL = @Value(report_url)
    TRANSFER_TIMEOUT_LENGTH = 300
    USE_COOKIES = No
    VERIFY_SSL_CERTIFICATES = No
    -> FeatureMerger_met_report_gegevens_3 [REQUESTOR]
    -> ListExploder_objectIds_2
Logger_3
    LOG_FEATURE = LOG_RECORD
    MAXCOORDS = 20
    MAXFEATS = 20
    MESSAGE = Feature is:
    SEVERITY = INFO
FoutCreateReport_3: Logger
    LOG_FEATURE = LOG_ONLY
    MAXCOORDS = 20
    MAXFEATS = 20
    MESSAGE = Feature is:
    SEVERITY = INFO
    LOGGED -> Terminator_3
Terminator_3
    MESSAGE = Translation Terminated

Bookmark: Update rapportagestatus deurinspecties en overige velden
ListExploder_objectIds_2
    ATTR_CONFLICT_RES_LOOKUP = INCOMING_IF_CONFLICT
    INDEX_ATTR = _element_index
    LIST_ATTR = resultInfo.succeededObjectIds{}
    ATTR_ACCUM_MODE = Merge List Attributes
    ATTR_CONFLICT_RES = Use List Attribute Values
    ELEMENTS -> AttributeKeeper_9
AttributeKeeper_9
    CREATE_BULK_MODE_FEATURES = NO
    KEEP_ATTRS = resultInfo.succeededObjectIds
    -> FeatureMerger_6 [REQUESTOR]
FeatureMerger_6
    ATTR_ACCUM_MODE = Merge Supplier
    ATTR_CONFLICT_RES_LOOKUP = REQUESTOR_IF_CONFLICT
    IGNORE_NULLS = No
    JOIN_KEYS = @Value(resultInfo.succeededObjectIds) @Value(OBJECTID) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeKeeper_10
AttributeKeeper_10
    CREATE_BULK_MODE_FEATURES = NO
    KEEP_ATTRS = Gerapporteerd,RapportageDatum,GlobalID
    -> AttributeManager_14
AttributeManager_14
    ATTR_TABLE:
      SET_TO Gerapporteerd (varchar(256)) = Ja
      SET_TO RapportageDatum (date) = @DateTimeNow()
    -> DateTimeConverter_naar_ARCGIS_format_3
DateTimeConverter_naar_ARCGIS_format_3
    DATETIME_ATTR = RapportageDatum
    OUT_FORMAT = %m/%d/%Y
    PASSTHROUGH = NO
    REPAIR_INPUT = YES
    -> WSHD_DL_Dakonderhoud (writer SAFE.ESRI-AGOL.ARCGISFEATURESERVICE_7)

Bookmark: Maak en verstuur mail
GKB_EmailGenerator_2
    ATTACHMENT = @Value(_response_file_path)
    Body = <H3>Rapportage dakonderhoud </H3> <br> Aan: $(WVB_EMAIL) <br><br>    Er zijn voor <font color=red>@Value(_numfeatures)</font> locaties meldingen voor dakonderhoud gedaan <br><br>@Value(_result)
    Subject = Rapportage @Value(Vandaag) @Value(_numfeatures) meldingen dakonderhoud @Value(ProjectCode)
    To = $(WVB_EMAIL)
    VERZAMEL_MAIL = YES

Bookmark: Bepalen laatst uitgevoerd dakonderhoud
Sorter_2
    SORT_PARM = LocatieCode NATURAL ASCENDING NON_VALUES_AFTER_VALUES DatumDakonderhoud NATURAL DESCENDING NON_VALUES_AFTER_VALUES
    SORTED -> Counter_3
Counter_3
    CNT_ATTR = _count
    GROUP_BY = LocatieCode
    SCOPE = Local
    START = 0
    -> TestFilter__count___0
TestFilter__count___0
    DEFAULT_VALUE = <UNFILTERED>
    PASSED_TEST_GROUP_OUTPUT = FIRST
    TEST_LIST = "BOOL_OP,OR,COMPOSITE_TEST,""""""1"""""",TEST_CLAUSE,TEST @Value(_count) = 0",_count = 0 -> laatst uitgevoerde dakonderhoud
    _count = 0 -> laatst uitgevoerde dakonderhoud -> AttributeManager_17
AttributeManager_17
    ATTR_TABLE:
      SET_TO JaarInterval (real64) = @Evaluate(@Value(JaarVandaag)-@Value(JaarOnderhoud))
      SET_TO StatusDakonderhoud (varchar(255)) = FME_CONDITIONAL:DEFAULT_VALUE'Uitvoeren'BOOL_OP;OR;COMPOSITE_TEST;1;TEST @Value(JaarInterval) = 0'@Value(StatusDakonderhoud)'FME_NUM_CONDITIONS2___
    -> AttributeKeeper_6
AttributeKeeper_6
    CREATE_BULK_MODE_FEATURES = NO
    KEEP_ATTRS = StatusDakonderhoud,LocatieCode,LocatieNaam
    -> FeatureMerger_4 [REQUESTOR]

Bookmark: Update incomplete deurinspecties
JSONExtractor_QRDeurType_3 [off]
    EXTRACT_QUERY_TABLE = QRDeurType json["DeurType"] QRLocatieCode json["LocatieCode"] QRLocatieNaam json["LocatieNaam"] QRLocatieType json["LocatieType"]
    JSON_DOCUMENT = @Value(QRDeur)
    READ_FROM_FILE = NO
    EVALUATED -> AttributeManager_2 [off]
AttributeManager_2 [off]
    ATTR_TABLE:
      SET_TO LocatieType (varchar(255)) = @Value(QRLocatieType)
      SET_TO LocatieNaam (varchar(255)) = @Value(QRLocatieNaam)
      SET_TO DeurType (varchar(255)) = @Value(QRDeurType)
      SET_TO LocatieCode (varchar(255)) = @Value(QRLocatieCode)
    -> AttributeKeeper_3 [off]
AttributeKeeper_3 [off]
    CREATE_BULK_MODE_FEATURES = NO
    KEEP_ATTRS = DeurType,LocatieCode,LocatieNaam,globalid,LocatieType
    -> WSHD_DL_Deurinspectie (writer SAFE.ESRI-AGOL.ARCGISFEATURESERVICE_4) [off]
WSHD_DL_Deurinspectie (writer SAFE.ESRI-AGOL.ARCGISFEATURESERVICE_4) [off]
    attributes: globalid GlobalID(38), LocatieNaam String(255), DeurType String(255), LocatieCode String(255), LocatieType String(255)

Bookmark: Documentatie
Note: 08-10-2025 1e versie derived from webhook versie om er een versie van te maken die 1x per dag alle inspecties van die dag rapporteert. / .... / 15-11-2025 Inbouwen verwerken dakonderhoud / 25-11-2025 Statuswijzigingen aanpassen in rapportage. Nu zijn er 3 statussen 'Gereed', 'Deels', 'Niet uitvoerbaar'. / 2-12-2025 Status locaties terugzetten als de nieuwste datum van dakonderhoud of deurinspectie langer dan 6 maanden geleden is. / 12-12-2025 Controle gegevens. Door haperende verbinding op de tablets zijn pulldata velden soms leeg. Deze alsnog vullen. Betreft LocatieNaam, LocatieType en AdresLabel. / 15-01-2026 Status locatie dakonderhoudop Uitvoeren zetten als de laatste dakinspectie van vorig jaar is.
Note: Process: / Lees alle deurinspecties uit en filter of geef een filter mee bij het uitlezen met de datum van vandaag. / Voer controles uit : / - QRCode aanwezig. Indien Nee dan is DeurNummer -1, nieuw deurnummer genereren op basis van de DeurType en volgnummer. Zie gegenereerde etiketten. Maak een melding per mail naar beheerder en werkvoorbereider. / - Check of DeurType in QR Code en de waarde in het veld DeurType hetzelfde zijn. Zo niet melding per email naar beheerder en werkvoorbereider. Er dient een nieuw etiket aangemaakt te worden en de oude vervangen.

Bookmark: Rapporteer storingen
Note: uploadInfo wordt niet toegeveoegd als parameter daarmee zijn de reports max 24 uur beschikbaar voor download. Dus niet opgeslagen in AGOL. / uploadInfo={"type":"arcgis","parameters":{"title":"@Value(outputFileName)","folderId":"@Value(mapID)"}} / https://developers.arcgis.com/survey123/api-reference/rest/report/

Bookmark: Rapporteer inspecties
Note: uploadInfo wordt niet toegeveoegd als parameter daarmee zijn de reports max 24 uur beschikbaar voor download. Dus niet opgeslagen in AGOL. / uploadInfo={"type":"arcgis","parameters":{"title":"@Value(outputFileName)","folderId":"@Value(mapID)"}} / https://developers.arcgis.com/survey123/api-reference/rest/report/

Bookmark: Rapporteer storingen
Note: uploadInfo wordt niet toegeveoegd als parameter daarmee zijn de reports max 24 uur beschikbaar voor download. Dus niet opgeslagen in AGOL. / uploadInfo={"type":"arcgis","parameters":{"title":"@Value(outputFileName)","folderId":"@Value(mapID)"}} / https://developers.arcgis.com/survey123/api-reference/rest/report/

FME custom transformer AttributeCombiner
Combines specified attribute(s) of multiple features to form concatenated string(s). This transformer outputs a single feature for each group of input features, and the specified attribute(s) in the output feature will store the concatenated string(s). 
    This transformer always discards <null> and <missing> attributes. Regarding the empty string, you can control how to handle that with the "Drop Empty String" parameter. 
    The function is similar to the "Attributes to Concatenate" option of the Aggregator, but this transformer does not aggregate features. The geometry and unspecified attributes of any one feature for each group will be preserved, but others will be discarded. 
    This transformer can be used to concatenate specific attributes of many features efficiently, if you don't need to perform feature aggregation.
    Note: This transformer contains a Python script, which was tested with both Python 2.7 and Python 3.x interpreters.
Parameters
    Group By
    : 
    If you specify one or more attributes in this parameter, the concatenation will be performed for each group of features which have the same value(s) for the specified attribute(s).
    Input is Ordered by Group
    :
    If you are sure that the input features are sorted by the "Group By" attributes, you can set "Yes" to this parameter so that the processing will be performed with the best performance.
    Attributes to Combine
    :
    Select attributes that should be combined.
    Maximum Number of Features to Combine
    :
    Optionally you can specify the maximum number of features to combine into one. The number must be an integer greater than 0. Otherwise, the setting will be ignored. 
    Note that the number specified with this parameter indicates the maximum number of processed features at once. The number of concatenated attributes could be less than the maximum, since <null> and <missing> (and <empty> if you set "Yes" to the "Drop Empty String" parameter) attributes will be discarded. 
    Drop Empty String
    :
    By default, this transformer treats the empty string as a valid value which should be concatenated. If you don't want to concatenate empty strings, set "Yes" to this parameter.
    Delimiter String
    :
    Specify a character string that should be used as a delimiter string to separate individual values. You can also leave blank this parameter not to use any delimiter.
    Surround Each Value With
    :
    Optionally you can select a pair of symbols (e.g. single quotation marks) that will surround each value before concatenating. 
    Prefix for Each Value
    : 
    Optionally you can specify a prefix string that will be added to each value. 
    Suffix for Each Value
    : 
    Optionally you can specify a suffix string that will be added to each value.

Parameters:
- GROUP_BY =   # " " Group By
- ORDERED_BY_GROUP = No   # Input is Ordered by Group
- ATTRS =   # " " Attributes to Combine
- MAX_NUM =   # Maximum Number of Features to Combine
- DROP_EMPTY = No   # Drop Empty String
- DELIM = ,   # " " Delimiter String
- QUOT = None
- PREFIX =   # " " Prefix for Each Value
- SUFFIX =   # " " Suffix for Each Value

Input (input)
    -> ParameterFetcher
ParameterFetcher
    ATTR_LIST = __tmp.group_by $(GROUP_BY) __tmp.attrs $(ATTRS) __tmp.max_num $(MAX_NUM) __tmp.delim $(DELIM) __tmp.drop_empty $(DROP_EMPTY) __tmp.quot $(QUOT) __tmp.prefix $(PREFIX) __tmp.suffix $(SUFFIX)
    -> TclCaller
TclCaller
    NEW_ATTRIBUTES = __tmp.attr{}
    SRC:
      proc preProcessToCombine {} {
          set i 0
          foreach attr [FME_GetAttribute "__tmp.attrs"] {
              FME_SetAttribute "__tmp.attr{$i}" $attr
              incr i
          }
          set num [FME_GetAttribute "__tmp.max_num"]
          if {![string is integer -strict $num]} {
              FME_SetAttribute "__tmp.max_num" 0
          }
          set group {}
          foreach attr [FME_GetAttribute "__tmp.group_by"] {
              if {![FME_AttributeExists $attr]} {
                  lappend group "\a"
              } elseif {[FME_IsAttributeNull $attr]} {
                  lappend group "\b"
              } else {
                  lappend group [FME_GetAttribute $attr]
              }
          }
          return [join $group {_}]
      }
    TCLPROG = preProcessToCombine
    VAL_ATTR = __tmp.group
    -> Tester
Tester
    BOOL_OP = OR
    TEST_CLAUSE:
      TEST @Value(__tmp.group_by) = ""
      TEST $(ORDERED_BY_GROUP) = Yes
    TEST_MODE = Automatic
    PASSED -> PythonCaller
    FAILED -> Sorter
Sorter
    SORT_PARM = __tmp.group ALPHA ASCENDING
    SORTED -> PythonCaller
PythonCaller
    PYTHONSOURCE:
      # 2016-04-13, Takashi Iijima, Original Implementation
      # 2018-05-07, Takashi Iijima, Suuports Python 3.x
      # 2020-01-13, Takashi Iijima, Changed Default Python Interpreter to 3.6+, saved with FME 2017.1.2.1

      import fme
      import fmeobjects, locale

      class AttributeCombiner(object):
          def __init__(self):
              import platform
              vt = platform.python_version_tuple()
              if vt[0] == '2':
                  loc = locale.getdefaultlocale()
                  enc = loc[1] if loc else 'utf_8'
                  self.toStr = lambda s: s.encode(enc) if isinstance(s, unicode) else str(s)
              else:
                  self.toStr = lambda s: s
              self.reset(None, None)

          def reset(self, group, feature):
              self.group = group # group ID value
              self.feature = feature # first feature for each group
              self.data = {} # key: attribute name, value: list of attribute values
              self.count = 0 # counter for number of features to combine

          def input(self, feature):
              group = feature.getAttribute('__tmp.group')
              num = int(feature.getAttribute('__tmp.max_num'))
              if group != self.group or (0 < num and num <= self.count):
                  self.output()
                  self.reset(group, feature)
              for attr in feature.getAttribute('__tmp.attr{}'):
                  attr = self.toStr(attr)
                  isNull, isMissing, type = feature.getAttributeNullMissingAndType(attr)
                  if not isNull and not isMissing:
                      self.data.setdefault(attr, []).append('%s' % feature.getAttribute(attr))
              self.count += 1

          def close(self):
              self.output()

          def output(self):
              if self.feature:
                  fmt = self.getFormat()
                  delim = self.feature.getAttribute('__tmp.delim')
                  if self.feature.getAttribute('__tmp.drop_empty') == 'Yes':
                      for attr, values in self.data.items():
                          self.feature.setAttribute(attr, delim.join([fmt % v for v in values if v != '']))
                  else:
                      for attr, values in self.data.items():
                          self.feature.setAttribute(attr, delim.join([fmt % v for v in values]))
                  self.pyoutput(self.feature)

          def getFormat(self):
              formats = {
                  'Single': '\'%s%%s%s\'' ,
                  'Double': '"%s%%s%s"' ,
                  'Round': '(%s%%s%s)',
                  'Curly': '{%s%%s%s}',
                  'Square': '[%s%%s%s]',
                  'Inequality': '<%s%%s%s>',
                  'None': '%s%%s%s'
              }
              option = self.feature.getAttribute('__tmp.quot')
              prefix= self.feature.getAttribute('__tmp.prefix')
              suffix = self.feature.getAttribute('__tmp.suffix')
              return formats[option] % (prefix, suffix)
    PYTHONSYMBOL = AttributeCombiner
    -> AttributeRemover
AttributeRemover
    LIST_ATTRS = __tmp.attr{}
    REMOVE_ATTRS = __tmp.attrs,__tmp.delim,__tmp.drop_empty,__tmp.group,__tmp.group_by,__tmp.max_num,__tmp.prefix,__tmp.quot,__tmp.suffix
    -> Output (output)
Output (output)

FME custom transformer FeatureCounter
This transformer counts the number of features passing through, and applies that number as an attribute onto each feature.
It differs from the Counter in that it gives the total count to each feature. It doesn't give each feature a unique, incremented number.
It differs from the StatisticsCalculator in that it does not need an attribute to be selected for analysis.
An optional group-by parameter allows features to be counted in groups.
Transformer Category: Calculated Values
Blocker Transformer: Yes

Parameters:
- GroupBox =   # Group Processing
- GROUP_BY =   # "" Group By
- GROUP_BY_MODE = No   # When All Features Received,No%When Group Changes (Advanced),Yes Complete Groups
- GeneralBox =   # FeatureCounterNewAttrParameter General
- FeatureCounterNewAttrParameter = _numfeatures   # New Attribute Name

Input (input)
    -> AttributeCreator_2
Note: Create temporary attribute for StatisticsCalculator
AttributeCreator_2
    ATTR_TABLE = SET_TO FeatureCounter_tempattr (int8) = 1
    -> StatisticsCalculator
Note: Calculate number of features
StatisticsCalculator
    ATTR_ACCUM_MODE = None
    CALCULATION_MODE = NUMERIC
    FEAT_STATS = FeatureCounter_tempattr,NUMERIC_MODE,,,COUNT,,,,,,,,,,
    GROUP_BY = $(GROUP_BY)
    PREPEND_ATTR_NAME_OBS = No
    STATISTIC_SUFFIX_RENAME_MAP = COUNT,FeatureCounter_tempattr_count
    COMPLETE -> AttributeCreator
Note: Create new attribute
AttributeCreator
    ATTR_TABLE = SET_TO $(FeatureCounterNewAttrParameter) (uint64) = @Value(FeatureCounter_tempattr_count)
    -> AttributeExposer
Note: Expose new attribute
AttributeExposer
    ATTR_TABLE = $(FeatureCounterNewAttrParameter),
    -> Output (output)
Note: Output features keeping only new attribute
Output (output)

FME custom transformer AttributeCombiner_2
Combines specified attribute(s) of multiple features to form concatenated string(s). This transformer outputs a single feature for each group of input features, and the specified attribute(s) in the output feature will store the concatenated string(s). 
    This transformer always discards <null> and <missing> attributes. Regarding the empty string, you can control how to handle that with the "Drop Empty String" parameter. 
    The function is similar to the "Attributes to Concatenate" option of the Aggregator, but this transformer does not aggregate features. The geometry and unspecified attributes of any one feature for each group will be preserved, but others will be discarded. 
    This transformer can be used to concatenate specific attributes of many features efficiently, if you don't need to perform feature aggregation.
    Note: This transformer contains a Python script, which was tested with both Python 2.7 and Python 3.x interpreters.
Parameters
    Group By
    : 
    If you specify one or more attributes in this parameter, the concatenation will be performed for each group of features which have the same value(s) for the specified attribute(s).
    Input is Ordered by Group
    :
    If you are sure that the input features are sorted by the "Group By" attributes, you can set "Yes" to this parameter so that the processing will be performed with the best performance.
    Attributes to Combine
    :
    Select attributes that should be combined.
    Maximum Number of Features to Combine
    :
    Optionally you can specify the maximum number of features to combine into one. The number must be an integer greater than 0. Otherwise, the setting will be ignored. 
    Note that the number specified with this parameter indicates the maximum number of processed features at once. The number of concatenated attributes could be less than the maximum, since <null> and <missing> (and <empty> if you set "Yes" to the "Drop Empty String" parameter) attributes will be discarded. 
    Drop Empty String
    :
    By default, this transformer treats the empty string as a valid value which should be concatenated. If you don't want to concatenate empty strings, set "Yes" to this parameter.
    Delimiter String
    :
    Specify a character string that should be used as a delimiter string to separate individual values. You can also leave blank this parameter not to use any delimiter.
    Surround Each Value With
    :
    Optionally you can select a pair of symbols (e.g. single quotation marks) that will surround each value before concatenating. 
    Prefix for Each Value
    : 
    Optionally you can specify a prefix string that will be added to each value. 
    Suffix for Each Value
    : 
    Optionally you can specify a suffix string that will be added to each value.

Parameters:
- GROUP_BY =   # " " Group By
- ORDERED_BY_GROUP = No   # Input is Ordered by Group
- ATTRS =   # " " Attributes to Combine
- MAX_NUM =   # Maximum Number of Features to Combine
- DROP_EMPTY = No   # Drop Empty String
- DELIM = ,   # " " Delimiter String
- QUOT = None
- PREFIX =   # " " Prefix for Each Value
- SUFFIX =   # " " Suffix for Each Value

Input (input)
    -> ParameterFetcher
ParameterFetcher
    ATTR_LIST = __tmp.group_by $(GROUP_BY) __tmp.attrs $(ATTRS) __tmp.max_num $(MAX_NUM) __tmp.delim $(DELIM) __tmp.drop_empty $(DROP_EMPTY) __tmp.quot $(QUOT) __tmp.prefix $(PREFIX) __tmp.suffix $(SUFFIX)
    -> TclCaller
TclCaller
    NEW_ATTRIBUTES = __tmp.attr{}
    SRC:
      proc preProcessToCombine {} {
          set i 0
          foreach attr [FME_GetAttribute "__tmp.attrs"] {
              FME_SetAttribute "__tmp.attr{$i}" $attr
              incr i
          }
          set num [FME_GetAttribute "__tmp.max_num"]
          if {![string is integer -strict $num]} {
              FME_SetAttribute "__tmp.max_num" 0
          }
          set group {}
          foreach attr [FME_GetAttribute "__tmp.group_by"] {
              if {![FME_AttributeExists $attr]} {
                  lappend group "\a"
              } elseif {[FME_IsAttributeNull $attr]} {
                  lappend group "\b"
              } else {
                  lappend group [FME_GetAttribute $attr]
              }
          }
          return [join $group {_}]
      }
    TCLPROG = preProcessToCombine
    VAL_ATTR = __tmp.group
    -> Tester
Tester
    BOOL_OP = OR
    TEST_CLAUSE:
      TEST @Value(__tmp.group_by) = ""
      TEST $(ORDERED_BY_GROUP) = Yes
    TEST_MODE = Automatic
    PASSED -> PythonCaller
    FAILED -> Sorter
Sorter
    SORT_PARM = __tmp.group ALPHA ASCENDING
    SORTED -> PythonCaller
PythonCaller
    PYTHONSOURCE:
      # 2016-04-13, Takashi Iijima, Original Implementation
      # 2018-05-07, Takashi Iijima, Suuports Python 3.x
      # 2020-01-13, Takashi Iijima, Changed Default Python Interpreter to 3.6+, saved with FME 2017.1.2.1

      import fme
      import fmeobjects, locale

      class AttributeCombiner(object):
          def __init__(self):
              import platform
              vt = platform.python_version_tuple()
              if vt[0] == '2':
                  loc = locale.getdefaultlocale()
                  enc = loc[1] if loc else 'utf_8'
                  self.toStr = lambda s: s.encode(enc) if isinstance(s, unicode) else str(s)
              else:
                  self.toStr = lambda s: s
              self.reset(None, None)

          def reset(self, group, feature):
              self.group = group # group ID value
              self.feature = feature # first feature for each group
              self.data = {} # key: attribute name, value: list of attribute values
              self.count = 0 # counter for number of features to combine

          def input(self, feature):
              group = feature.getAttribute('__tmp.group')
              num = int(feature.getAttribute('__tmp.max_num'))
              if group != self.group or (0 < num and num <= self.count):
                  self.output()
                  self.reset(group, feature)
              for attr in feature.getAttribute('__tmp.attr{}'):
                  attr = self.toStr(attr)
                  isNull, isMissing, type = feature.getAttributeNullMissingAndType(attr)
                  if not isNull and not isMissing:
                      self.data.setdefault(attr, []).append('%s' % feature.getAttribute(attr))
              self.count += 1

          def close(self):
              self.output()

          def output(self):
              if self.feature:
                  fmt = self.getFormat()
                  delim = self.feature.getAttribute('__tmp.delim')
                  if self.feature.getAttribute('__tmp.drop_empty') == 'Yes':
                      for attr, values in self.data.items():
                          self.feature.setAttribute(attr, delim.join([fmt % v for v in values if v != '']))
                  else:
                      for attr, values in self.data.items():
                          self.feature.setAttribute(attr, delim.join([fmt % v for v in values]))
                  self.pyoutput(self.feature)

          def getFormat(self):
              formats = {
                  'Single': '\'%s%%s%s\'' ,
                  'Double': '"%s%%s%s"' ,
                  'Round': '(%s%%s%s)',
                  'Curly': '{%s%%s%s}',
                  'Square': '[%s%%s%s]',
                  'Inequality': '<%s%%s%s>',
                  'None': '%s%%s%s'
              }
              option = self.feature.getAttribute('__tmp.quot')
              prefix= self.feature.getAttribute('__tmp.prefix')
              suffix = self.feature.getAttribute('__tmp.suffix')
              return formats[option] % (prefix, suffix)
    PYTHONSYMBOL = AttributeCombiner
    -> AttributeRemover
AttributeRemover
    LIST_ATTRS = __tmp.attr{}
    REMOVE_ATTRS = __tmp.attrs,__tmp.delim,__tmp.drop_empty,__tmp.group,__tmp.group_by,__tmp.max_num,__tmp.prefix,__tmp.quot,__tmp.suffix
    -> Output (output)
Output (output)

FME custom transformer GKB_EmailGenerator
GKB_EmailGenerator
Send a mail using the FME Flow notification API.
Input : Verzamelmail, To, CC, Subject, Body and Attachment. 
- Attachment must be de full path to the file.
- Verzamelmail is Ja/Nee. If YES then one mail is made for all incoming features with the attachments combined.
Output The http_status_code and response_body from the httpcaller sending the mail.
Use

Parameters:
- EMAIL =   # Email instellingen
- VERZAMEL_MAIL = YES   # Maak verzamelmail
- To =
- CC =
- Subject =
- Body =   # Body text
- ATTACHMENT =   # Attachment (full path)

Input (input)
    -> Counter_tel_features
AttributeCreator_4
    ATTR_TABLE:
      SET_TO body (varchar(200)) = {
            "email_to": "$(To)",
            "email_cc": "$(CC)",
            "email_bcc": "",
            "email_from": "gis@gkbgroep.nl",
            "email_replyto": "",
            "email_subject": "$(Subject)",
            "subscriber_content": "$(Body)",
            @Value(_attachment_regel)
        }
      SET_TO url (varchar(78)) = https://fme-gkb.fmecloud.com/fmerest/v3/notifications/topics/SEND_MAIL/message
      SET_TO token (varchar(40)) = cabe43c16dfd6e481e2f2b6fbb5369ed9df0175e
    -> HTTPCaller_2
HTTPCaller_2
    CLIENT_CERTIFICATE_TYPE = NONE
    CONNECTION_TIMEOUT_LENGTH = 60
    CONTENT_TYPE_LOOKUP = application/json
    CUSTOM_HEADERS = Authorization;fmetoken token=@Value(token)
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = @Value(url)
    TRANSFER_TIMEOUT_LENGTH = 90
    UPLOAD_BODY = @Value(body)
    UPLOAD_TYPE = STRING_UPLOAD
    USE_COOKIES = No
    VERIFY_SSL_CERTIFICATES = Yes
    UPLOAD_CONTENT_TYPE = JSON (application/json)
    -> Output (output)
Output (output)
UniqueValueLogger
    VAL = @Value(_count)

Bookmark: Maak nep json als gebruikt voor email subscription
Counter_tel_features
    CNT_ATTR = _count
    SCOPE = Local
    START = 0
    -> StringConcatenator_2
StringConcatenator_2
    ACTION = Create New Attribute
    PARM_LINE = "email_attachment{@Value(_count)}": "@Value(Attachment)"
    VAL_ATTR = _attachment_regel
    -> TestFilter
    -> UniqueValueLogger
TestFilter
    DEFAULT_VALUE = Losse mails
    PASSED_TEST_GROUP_OUTPUT = FIRST
    TEST_LIST = "BOOL_OP,OR,COMPOSITE_TEST,""""""1"""""",TEST_CLAUSE,TEST $(VERZAMEL_MAIL) = YES",Verzamelmail
    Verzamelmail -> AttributeCombiner_2
    Losse mails -> AttributeCreator_4
AttributeCombiner_2
    ATTRS = _attachment_regel
    DELIM = ,
    DROP_EMPTY = Yes
    QUOT = None
    -> AttributeCreator_4

FME custom transformer AttributeCombiner_3
Combines specified attribute(s) of multiple features to form concatenated string(s). This transformer outputs a single feature for each group of input features, and the specified attribute(s) in the output feature will store the concatenated string(s). 
    This transformer always discards <null> and <missing> attributes. Regarding the empty string, you can control how to handle that with the "Drop Empty String" parameter. 
    The function is similar to the "Attributes to Concatenate" option of the Aggregator, but this transformer does not aggregate features. The geometry and unspecified attributes of any one feature for each group will be preserved, but others will be discarded. 
    This transformer can be used to concatenate specific attributes of many features efficiently, if you don't need to perform feature aggregation.
    Note: This transformer contains a Python script, which was tested with both Python 2.7 and Python 3.x interpreters.
Parameters
    Group By
    : 
    If you specify one or more attributes in this parameter, the concatenation will be performed for each group of features which have the same value(s) for the specified attribute(s).
    Input is Ordered by Group
    :
    If you are sure that the input features are sorted by the "Group By" attributes, you can set "Yes" to this parameter so that the processing will be performed with the best performance.
    Attributes to Combine
    :
    Select attributes that should be combined.
    Maximum Number of Features to Combine
    :
    Optionally you can specify the maximum number of features to combine into one. The number must be an integer greater than 0. Otherwise, the setting will be ignored. 
    Note that the number specified with this parameter indicates the maximum number of processed features at once. The number of concatenated attributes could be less than the maximum, since <null> and <missing> (and <empty> if you set "Yes" to the "Drop Empty String" parameter) attributes will be discarded. 
    Drop Empty String
    :
    By default, this transformer treats the empty string as a valid value which should be concatenated. If you don't want to concatenate empty strings, set "Yes" to this parameter.
    Delimiter String
    :
    Specify a character string that should be used as a delimiter string to separate individual values. You can also leave blank this parameter not to use any delimiter.
    Surround Each Value With
    :
    Optionally you can select a pair of symbols (e.g. single quotation marks) that will surround each value before concatenating. 
    Prefix for Each Value
    : 
    Optionally you can specify a prefix string that will be added to each value. 
    Suffix for Each Value
    : 
    Optionally you can specify a suffix string that will be added to each value.

Parameters:
- GROUP_BY =   # " " Group By
- ORDERED_BY_GROUP = No   # Input is Ordered by Group
- ATTRS =   # " " Attributes to Combine
- MAX_NUM =   # Maximum Number of Features to Combine
- DROP_EMPTY = No   # Drop Empty String
- DELIM = ,   # " " Delimiter String
- QUOT = None
- PREFIX =   # " " Prefix for Each Value
- SUFFIX =   # " " Suffix for Each Value

Input (input)
    -> ParameterFetcher
ParameterFetcher
    ATTR_LIST = __tmp.group_by $(GROUP_BY) __tmp.attrs $(ATTRS) __tmp.max_num $(MAX_NUM) __tmp.delim $(DELIM) __tmp.drop_empty $(DROP_EMPTY) __tmp.quot $(QUOT) __tmp.prefix $(PREFIX) __tmp.suffix $(SUFFIX)
    -> TclCaller
TclCaller
    NEW_ATTRIBUTES = __tmp.attr{}
    SRC:
      proc preProcessToCombine {} {
          set i 0
          foreach attr [FME_GetAttribute "__tmp.attrs"] {
              FME_SetAttribute "__tmp.attr{$i}" $attr
              incr i
          }
          set num [FME_GetAttribute "__tmp.max_num"]
          if {![string is integer -strict $num]} {
              FME_SetAttribute "__tmp.max_num" 0
          }
          set group {}
          foreach attr [FME_GetAttribute "__tmp.group_by"] {
              if {![FME_AttributeExists $attr]} {
                  lappend group "\a"
              } elseif {[FME_IsAttributeNull $attr]} {
                  lappend group "\b"
              } else {
                  lappend group [FME_GetAttribute $attr]
              }
          }
          return [join $group {_}]
      }
    TCLPROG = preProcessToCombine
    VAL_ATTR = __tmp.group
    -> Tester
Tester
    BOOL_OP = OR
    TEST_CLAUSE:
      TEST @Value(__tmp.group_by) = ""
      TEST $(ORDERED_BY_GROUP) = Yes
    TEST_MODE = Automatic
    PASSED -> PythonCaller
    FAILED -> Sorter
Sorter
    SORT_PARM = __tmp.group ALPHA ASCENDING
    SORTED -> PythonCaller
PythonCaller
    PYTHONSOURCE:
      # 2016-04-13, Takashi Iijima, Original Implementation
      # 2018-05-07, Takashi Iijima, Suuports Python 3.x
      # 2020-01-13, Takashi Iijima, Changed Default Python Interpreter to 3.6+, saved with FME 2017.1.2.1

      import fme
      import fmeobjects, locale

      class AttributeCombiner(object):
          def __init__(self):
              import platform
              vt = platform.python_version_tuple()
              if vt[0] == '2':
                  loc = locale.getdefaultlocale()
                  enc = loc[1] if loc else 'utf_8'
                  self.toStr = lambda s: s.encode(enc) if isinstance(s, unicode) else str(s)
              else:
                  self.toStr = lambda s: s
              self.reset(None, None)

          def reset(self, group, feature):
              self.group = group # group ID value
              self.feature = feature # first feature for each group
              self.data = {} # key: attribute name, value: list of attribute values
              self.count = 0 # counter for number of features to combine

          def input(self, feature):
              group = feature.getAttribute('__tmp.group')
              num = int(feature.getAttribute('__tmp.max_num'))
              if group != self.group or (0 < num and num <= self.count):
                  self.output()
                  self.reset(group, feature)
              for attr in feature.getAttribute('__tmp.attr{}'):
                  attr = self.toStr(attr)
                  isNull, isMissing, type = feature.getAttributeNullMissingAndType(attr)
                  if not isNull and not isMissing:
                      self.data.setdefault(attr, []).append('%s' % feature.getAttribute(attr))
              self.count += 1

          def close(self):
              self.output()

          def output(self):
              if self.feature:
                  fmt = self.getFormat()
                  delim = self.feature.getAttribute('__tmp.delim')
                  if self.feature.getAttribute('__tmp.drop_empty') == 'Yes':
                      for attr, values in self.data.items():
                          self.feature.setAttribute(attr, delim.join([fmt % v for v in values if v != '']))
                  else:
                      for attr, values in self.data.items():
                          self.feature.setAttribute(attr, delim.join([fmt % v for v in values]))
                  self.pyoutput(self.feature)

          def getFormat(self):
              formats = {
                  'Single': '\'%s%%s%s\'' ,
                  'Double': '"%s%%s%s"' ,
                  'Round': '(%s%%s%s)',
                  'Curly': '{%s%%s%s}',
                  'Square': '[%s%%s%s]',
                  'Inequality': '<%s%%s%s>',
                  'None': '%s%%s%s'
              }
              option = self.feature.getAttribute('__tmp.quot')
              prefix= self.feature.getAttribute('__tmp.prefix')
              suffix = self.feature.getAttribute('__tmp.suffix')
              return formats[option] % (prefix, suffix)
    PYTHONSYMBOL = AttributeCombiner
    -> AttributeRemover
AttributeRemover
    LIST_ATTRS = __tmp.attr{}
    REMOVE_ATTRS = __tmp.attrs,__tmp.delim,__tmp.drop_empty,__tmp.group,__tmp.group_by,__tmp.max_num,__tmp.prefix,__tmp.quot,__tmp.suffix
    -> Output (output)
Output (output)

FME custom transformer UniqueValueLogger
This transformer lists all unique values for a chosen attribute, along with a count of the number of occurrences for each value. The information is logged in both the Translation Window/Workspace log file and stored in attributes.
This transformer is useful when creating a workspace, and you need to know the possible values to use in a filter.
Input Ports
Input: This transformer accepts any features with an attribute.
Output Ports
Output: Features are output with the attribute selected as the unique value to filter, and a new attribute containing the number of occurrences of each unique value. All other attributes are removed. 
_count: Number of occurrences of each unique value.
_value: Unique values of selected attribute.
Parameters
Attribute to Analyze: Select the attribute for the transformer to run analysis on. 
Notes
Transformer alternatives:
Duplicate Filter - Consider using this transformer if you are looking to get a list of unique values and do not need a _count attribute 
StatisticsCalculator - Setting the Group By mode to the attribute to analyze will produce the same result as this transformer. It may be useful if you would like to gather other statistics, as well as the count of the unique attributes.

Parameters:
- VAL =   # Attribute to Analyze

Input (input)
    -> AttributeCreator

Bookmark: Count unique attribute values
AttributeCreator
    ATTR_TABLE = SET_TO _value (varchar(200)) = $(VAL)
    -> AttributeKeeper
Note: Remove unwanted / attributes
AttributeKeeper
    CREATE_BULK_MODE_FEATURES = NO
    KEEP_ATTRS = _value
    -> Aggregator
Note: Create aggregates of / features, grouped by / the target attribute value
Aggregator
    ACCUM_ATTRS = All
    AGGREGATE_TYPE = Homogeneous Collection (If Possible)
    COUNT_ATTR = _count
    GROUP_BY = _value
    MODE = Geometry - Assemble One Level
    SEP = ,
    AGGREGATE -> StringConcatenator
Note: Concatenate unique values / with their occurrence counts
StringConcatenator
    ACTION = Create New Attribute
    PARM_LINE = fme_basicstring:14%1%14%1:@Value(_value),@Value(_count)
    VAL_ATTR = _concatenated
    -> Sorter
Note: Sort output based on / occurrence count and / attribute value
Sorter
    SORT_PARM = _count NUMERIC DESCENDING NON_VALUES_AFTER_VALUES _value ALPHA ASCENDING NON_VALUES_BEFORE_VALUES
    SORTED -> ListBuilder
    SORTED -> AttributeManager

Bookmark: Create output
AttributeManager
    ATTR_TABLE = REMOVE _concatenated (buffer)
    -> Output (output)
Output (output)

Bookmark: Log unique attribute values
Note: Turn all input features / Into a single list
ListBuilder
    LIST_NAME = _list
    -> ListConcatenator
Note: Concatenate values of / the list into an attribute
ListConcatenator
    DROP_EMPTY_PARTS = No
    LIST_ATTR = _list{}._concatenated
    VAL_ATTR = UNIQUE VALUES
    -> StringConcatenator_2
Note: Add header
StringConcatenator_2
    ACTION = Create New Attribute
    PARM_LINE = "\n\nVALUE, COUNT\n@Value(UNIQUE VALUES)\n"
    VAL_ATTR = UNIQUE VALUES
    -> AttributeRemover_2
Note: Remote the list
AttributeRemover_2
    LIST_ATTRS = _list{}
    -> Logger
Note: Log the single feature / that contains the / output attribute
Logger
    LOG_FEATURE = LOG_RECORD
    MAXCOORDS = 1
    MAXFEATS = 1
    MESSAGE = Unique values:
    SEVERITY = INFO

FME custom transformer JobStatusLooper

Parameters:
- JOBURL = @Value(JobURL)   # JobURL

JobStatus_Input (input)
    -> JobStatus
JobStatus: HTTPCaller
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 1
    REDIRECT_AUTH = ORIGINAL_DOMAIN_ONLY
    SAVE_FILE_LOOKUP = NO
    STATUS_CODE_ATTR = _http_status_code
    TARGET_ATTR = _JobStatus
    TARGET_ATTR_ENCODING = auto-detect
    TARGET_URL = @Value(JobURL)
    TRANSFER_TIMEOUT_LENGTH = 90
    USE_COOKIES = No
    VERIFY_SSL_CERTIFICATES = Yes
    SAVE_FILE = Attribute
    -> JSONFlattener
    <REJECTED> -> Junction
JSONFlattener
    ERROR_LIST_ATTR = _json_error
    JSON_DOCUMENT = @Value(_JobStatus)
    NEW_ATTRIBUTES = jobStatus jobId
    READ_FROM_FILE = NO
    RECURSIVE_LOOKUP = NO
    RECURSIVE = No
    -> TestFilter
    <REJECTED> -> Junction_2
TestFilter
    DEFAULT_VALUE = Failed
    PASSED_TEST_GROUP_OUTPUT = FIRST
    TEST_LIST:
      "BOOL_OP,OR,COMPOSITE_TEST,""""""1 OR 2"""""",TEST_CLAUSE,TEST @Value(jobStatus) = esriJobSucceeded
      TEST @Value(jobStatus) = esriJobPartialSucceeded",Success,"BOOL_OP,OR,COMPOSITE_TEST,""""""1"""""",TEST_CLAUSE,TEST @Value(jobStatus) = esriJobExecuting",Executing
    Success -> JobSuccess (output)
    Executing -> Decelerator
    Failed -> TestFilter_Failed
    Failed -> JobError (output)
JobSuccess (output)
JobError (output)
Decelerator
    DECEL_LOOKUP = PERFEATDELAY
    DELAY = 1
    DECEL_TYPE = Per Feature Delay
    -> JobStatus_Input (output)
JobStatus_Input (output)
TestFilter_Failed: Inspector [off]
Junction_2
Junction

FME custom transformer AGOL_GetToken_gisadmin

Parameters:
- User = gisadmin_GKB   # Username
- Password =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   # Enter a Password

HTTPCaller_Input (input)
    -> HTTPCaller
HTTPCaller
    ADDITIONAL_URL_PARAMETERS = referer;https://www.arcgis.com/ f;json
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    MULTIPARTS = username StringUpload SOURCE_EXPRESSION;$(User);MIME_TYPE;text/plain;FME_CONTROLLER_QUERY_FILE;transformers/dependencies/http/StringUpload.fme;FME_CONTROLLER_CHOICE;StringUpload password StringUpload SOURCE_EXPRESSION;$(Password);MIME_TYPE;text/plain;FME_CONTROLLER_QUERY_FILE;transformers/dependencies/http/StringUpload.fme;FME_CONTROLLER_CHOICE;StringUpload
    REDIRECT_AUTH = ORIGINAL_DOMAIN_ONLY
    SAVE_FILE_LOOKUP = NO
    STATUS_CODE_ATTR = _http_status_code
    TARGET_ATTR = _token
    TARGET_ATTR_ENCODING = auto-detect
    TARGET_URL = https://www.arcgis.com/sharing/generateToken
    TRANSFER_TIMEOUT_LENGTH = 90
    UPLOAD_TYPE = Multipart / Form Data
    USE_COOKIES = No
    VERIFY_SSL_CERTIFICATES = Yes
    SAVE_FILE = Attribute
    -> JSONFlattener
JSONFlattener
    ERROR_LIST_ATTR = _json_error
    JSON_DOCUMENT = @Value(_token)
    NEW_ATTRIBUTES = token
    READ_FROM_FILE = NO
    RECURSIVE_LOOKUP = YES
    RECURSIVE = Yes
    -> AttributeExposer_Output (output)
AttributeExposer_Output (output)

FME workspace UWVG_ChangeDetector.fmw

Parameters:
- EMAIL_TO = koen@gkbgroep.nl   # To

Readers:
- POSTGIS_6: POSTGIS from Local-Vastgoed
- POSTGIS_7: POSTGIS from Local-Vastgoed

Writers:
- POSTGIS_1: POSTGIS to FME-PostGIS-Vastgoed
- POSTGIS_3: POSTGIS to FME-PostGIS-Vastgoed
- POSTGIS_4: POSTGIS to Local-Vastgoed
- POSTGIS_5: POSTGIS to Local-Vastgoed

Note: DOCUMENTATIE / 16-03-2026 VorigeWeeknummer toegevoegd en gebruikt in bestandsnaam en email.
PythonCaller_PythonCaller_Hide_worksheets
    INPUT_PORT_CONNECTED = CONNECTED
    PYTHONSOURCE:
      import fme
      from fme import BaseTransformer
      import fmeobjects


      class FeatureProcessor(BaseTransformer):
          """Template Class Interface:
          When using this class, make sure its name is set as the value of the 'Class to Process Features'
          transformer parameter.

          This class inherits from 'fme.BaseTransformer'. For full details of this class, its methods, and
          expected usage, see https://docs.safe.com/fme/html/fmepython/api/fme.html#fme.BaseTransformer.
          """

          def __init__(self):
              """Base constructor for class members."""
              pass

          def has_support_for(self, support_type: int):
              """This method is called by FME to determine if the PythonCaller supports Bulk mode,
              which allows for significant performance gains when processing large numbers of features.
              """
              return support_type == fmeobjects.FME_SUPPORT_FEATURE_TABLE_SHIM

          def input(self, feature: fmeobjects.FMEFeature):
              """This method is called for each feature which enters the PythonCaller."""
              xlsx_path = feature.getAttribute('_dataset')  # or r"C:\temp\out.xlsx"
              sheet_to_hide = feature.getAttribute('name')  # or "Sheet1"

              try:
                  import openpyxl
              except ImportError:
                  feature.setAttribute('python_error', 'openpyxl not installed in this FME Python environment')
                  self.pyoutput(feature)
                  return

              wb = openpyxl.load_workbook(xlsx_path)
              if sheet_to_hide in wb.sheetnames:
                  ws = wb[sheet_to_hide]
                  ws.sheet_state = 'hidden'   # use 'veryHidden' if you want it not unhideable via Excel UI
                  wb.save(xlsx_path)
                  feature.setAttribute('sheet_hidden', sheet_to_hide)
              else:
                  feature.setAttribute('python_error', f'Sheet not found: {sheet_to_hide}')

              self.pyoutput(feature, output_tag="PYOUTPUT")


          def close(self):
              """This method is called once all the FME Features have been processed from input()."""
              pass

          def process_group(self):
              """This method is called by FME for each group when group processing mode is enabled."""
              pass

          def reject_feature(self, feature: fmeobjects.FMEFeature, code: str, message: str):
              """This method can be used to output a feature to the <Rejected> port."""
              feature.setAttribute("fme_rejection_code", code)
              feature.setAttribute("fme_rejection_message", message)
              self.pyoutput(feature, output_tag="<Rejected>")
    PYTHONSYMBOL = FeatureProcessor
    -> DuplicateFilter_2

Bookmark: INIT
Creator
    GEOMTYPE = Geometry Object
    NUM = 1
    CREATED -> PythonCaller_weeknummer
PythonCaller_weeknummer
    INPUT_PORT_CONNECTED = CONNECTED
    NEW_ATTRIBUTES = _start_week buffer
    PYTHONSOURCE:
      import fme
      from fme import BaseTransformer
      import fmeobjects
      import datetime
      from datetime import date


      class FeatureProcessor(BaseTransformer):
          """Template Class Interface:
          When using this class, make sure its name is set as the value of the 'Class to Process Features'
          transformer parameter.

          This class inherits from 'fme.BaseTransformer'. For full details of this class, its methods, and
          expected usage, see https://docs.safe.com/fme/html/fmepython/api/fme.html#fme.BaseTransformer.
          """

          def __init__(self):
              """Base constructor for class members."""
              pass

          def has_support_for(self, support_type: int):
              """This method is called by FME to determine if the PythonCaller supports Bulk mode,
              which allows for significant performance gains when processing large numbers of features.
              """
              return support_type == fmeobjects.FME_SUPPORT_FEATURE_TABLE_SHIM

          def input(self, feature: fmeobjects.FMEFeature):
              """This method is called for each feature which enters the PythonCaller."""
              # Assuming format YYYY-MM-DD
              _startdatum = datetime.datetime.now()
              # returns (ISOyear, ISOweek, ISOweekday)
              startyear, startweek, startweekday = _startdatum.isocalendar()
              feature.setAttribute('_start_week', startweek)
              self.pyoutput(feature, output_tag="PYOUTPUT")

          def close(self):
              """This method is called once all the FME Features have been processed from input()."""
              pass

          def process_group(self):
              """This method is called by FME for each group when group processing mode is enabled."""
              pass

          def reject_feature(self, feature: fmeobjects.FMEFeature, code: str, message: str):
              """This method can be used to output a feature to the <Rejected> port."""
              feature.setAttribute("fme_rejection_code", code)
              feature.setAttribute("fme_rejection_message", message)
              self.pyoutput(feature, output_tag="<Rejected>")
    PYTHONSYMBOL = FeatureProcessor
    -> AttributeCreator_datumstamp_en_paden
AttributeCreator_datumstamp_en_paden
    ATTR_TABLE:
      SET_TO DatumStamp (varchar(200)) = @DateTimeFormat(@DateTimeNow(),%Y%m%d%H%M)
      SET_TO VorigeWeeknummer (real64) = @Evaluate(@Value(_start_week) - 1)
      SET_TO DoelPath (varchar(200)) = FME_CONDITIONAL:DEFAULT_VALUE'$(FME_SHAREDRESOURCE_DATA)UWVG/RooienSnoeien/DataCheck_@Value(DatumStamp)'BOOL_OP;OR;COMPOSITE_TEST;1;TEST $(FME_OS) = Windows'$(FME_SHAREDRESOURCE_DATA)\UWVG\RooienSnoeien\DataCheck_@Value(DatumStamp)'FME_NUM_CONDITIONS2___
      SET_TO ExcelRooienDoelbestand (varchar(200)) = UWVG_RooienBomen_DataCheck_w@Value(VorigeWeeknummer)_@Value(DatumStamp).xlsx
      SET_TO ExcelSnoeienDoelbestand (varchar(200)) = UWVG_SnoeienBomen_DataCheck_w@Value(VorigeWeeknummer)_@Value(DatumStamp).xlsx
      SET_TO ExcelRooienDoelPath (varchar(200)) = FME_CONDITIONAL:DEFAULT_VALUE'@Value(DoelPath)/@Value(ExcelRooienDoelbestand)'BOOL_OP;OR;COMPOSITE_TEST;1;TEST $(FME_OS) = Windows'@Value(DoelPath)\@Value(ExcelRooienDoelbestand)'FME_NUM_CONDITIONS2___
      SET_TO ExcelSnoeienDoelPath (varchar(200)) = FME_CONDITIONAL:DEFAULT_VALUE'@Value(DoelPath)/@Value(ExcelSnoeienDoelbestand)'BOOL_OP;OR;COMPOSITE_TEST;1;TEST $(FME_OS) = Windows'@Value(DoelPath)\@Value(ExcelSnoeienDoelbestand)'FME_NUM_CONDITIONS2___
      SET_TO xlsx_sheet_visible (varchar(6)) = hidden
    INPUT_PORT_CONNECTED = CONNECTED
    -> FeatureReader [INITIATOR]
    -> FeatureReader_2 [INITIATOR]
    -> FeatureReader_3 [INITIATOR]
    -> AttributeCreator
AttributeCreator
    ATTR_TABLE:
      SET_TO StatusRooien (varchar(51)) = Ongewijzigd;Gewijzigd;Gerooid;Verwijderd;Toegevoegd
      SET_TO StatusSnoeien (varchar(52)) = Ongewijzigd;Gewijzigd;Gesnoeid;Verwijderd;Toegevoegd
      SET_TO Aantal (uint8) = 0
      SET_TO xlsx_sheet_visible (varchar(6)) = hidden
    INPUT_PORT_CONNECTED = CONNECTED
    -> AttributeSplitter_StatusRooien
    -> AttributeSplitter_StatusSnoeien
    -> FeatureMerger_3 [SUPPLIER]
    -> FeatureMerger_4 [SUPPLIER]
AttributeSplitter_StatusRooien
    ATTR_NAME = StatusRooien
    DELIMITER = ;
    DROP_EMPTY_PARTS = NO
    LIST_NAME = _list
    TRIM_TYPE = BOTH
    -> ListExploder_5
ListExploder_5
    ATTR_CONFLICT_RES_LOOKUP = INCOMING_IF_CONFLICT
    INDEX_ATTR = _element_index
    LIST_ATTR = _list{}
    ATTR_ACCUM_MODE = Merge List Attributes
    ATTR_CONFLICT_RES = Use List Attribute Values
    ELEMENTS -> AttributeManager_6
AttributeManager_6
    ATTR_TABLE:
      REMOVE StatusRooien (varchar(51))
      REMOVE StatusSnoeien (varchar(52))
      REMOVE _creation_instance (uint64)
      RENAME_SET_VALUE _list > Status (varchar(200))
      REMOVE _element_index (uint32)
    -> FeatureMerger [REQUESTOR]
AttributeSplitter_StatusSnoeien
    ATTR_NAME = StatusSnoeien
    DELIMITER = ;
    DROP_EMPTY_PARTS = NO
    LIST_NAME = _list
    TRIM_TYPE = BOTH
    -> ListExploder_6
ListExploder_6
    ATTR_CONFLICT_RES_LOOKUP = INCOMING_IF_CONFLICT
    INDEX_ATTR = _element_index
    LIST_ATTR = _list{}
    ATTR_ACCUM_MODE = Merge List Attributes
    ATTR_CONFLICT_RES = Use List Attribute Values
    ELEMENTS -> AttributeManager_7
AttributeManager_7
    ATTR_TABLE:
      REMOVE StatusRooien (varchar(51))
      REMOVE StatusSnoeien (varchar(52))
      REMOVE _creation_instance (uint64)
      RENAME_SET_VALUE _list > Status (varchar(200))
      REMOVE _element_index (uint32)
    -> FeatureMerger_2 [SUPPLIER]

Bookmark: "https://services.arcgis.com/zP1tGdLpGvt2qNJ6/arcgis/rest/services/Bomenrooi_Vastgvoed_IOB/FeatureServer/0"
FeatureReader_3
    ATTRIBUTES = Faunacontrole,"Aanwezig,Nest_aanwezig,Holten_scheuren_gaten,Loshangende_schors,Rooien,Opmerking,OBJECTID,BEHEEROBJECTOMSCHRIJVING,BOOMSORTIMENT,BUURT,DIAMETER,ID,STRAAT,WIJK,WOONPLAATS,MAATREGEL,INSPECTIE_DATUM,OBJECTID_1,CreationDate,Creator,EditDate,Editor,BRON,ID_MAATREGEL,Controleur_faunacheck,Datum_Kapvergunning_aangevraagd,Kapvergunning_aangevraagd_door,Datum_Gerooid,Escalatiedatum_te_rooien,Gerooid_door,OBJECTID_2,Status_kapvergunning,Boom_gerooid,opmerking_uitvoering,KV_geldig_vanaf,SCHADE,Toelichting_Inspectie,GlobalID,CreationDate_1,Creator_1,EditDate_1,Editor_1,BEHEERDER,Dat_acc_rooi,BOOMSTATUS,OPMERKINGEN,EIGENAAR,X,Y,stam_omtrek,PLAATSAANDUIDING,GEVOLG,Bewonend,ONDERHOUDSPLOEG"
    ATTR_ACCUM_MODE = Merge Initiator and Result
    ATTR_CONFLICT_RES = Use Result
    ATTR_IGNORE_NULLS = No
    CLIP_TO_ENVELOPE = NO
    COMBINE_GEOM = Use Result
    FEATURETYPES = Faunacontrole
    FORMAT = SAFE.ESRI-AGOL.ARCGISFEATURESERVICE
    GEOMETRY_TYPES = Faunacontrole,""",fme_point"""
    INITIATOR_FIRST_OUTPUT = default
    INPUT_PORT_INITIATOR_CONNECTED = CONNECTED
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    SAFE.ESRI-AGOL.ARCGISFEATURESERVICE_AGOL_AUTH_NC = Esri ArcGIS Online (gisadmin_GKB)
    SAFE.ESRI-AGOL.ARCGISFEATURESERVICE_ALIAS_MODE = NONE
    SAFE.ESRI-AGOL.ARCGISFEATURESERVICE_CREATE_FEATURE_TABLES_FROM_DATA = Yes
    SAFE.ESRI-AGOL.ARCGISFEATURESERVICE_FEATURES_PER_REQUEST = 1000
    SAFE.ESRI-AGOL.ARCGISFEATURESERVICE_FEATURE_SERVICE_WITH_ID = Bomenrooi Vastgoed IOB(1351f4c20ad24fbd9c84cf3b1f07e5a3)
    SAFE.ESRI-AGOL.ARCGISFEATURESERVICE_FORMAT_DATETIME = FME_FORMAT
    SAFE.ESRI-AGOL.ARCGISFEATURESERVICE_FORMAT_GLOBALID = NO_FORMAT
    SAFE.ESRI-AGOL.ARCGISFEATURESERVICE_GROUP_ID = 9ffcaef4941d4fa48e8ef34e6a3acad1
    SAFE.ESRI-AGOL.ARCGISFEATURESERVICE_QUERY_FEATURE_TYPES_FOR_MERGE_FILTERS = Yes
    SAFE.ESRI-AGOL.ARCGISFEATURESERVICE_RESOLVE_DOMAINS = NO
    SAFE.ESRI-AGOL.ARCGISFEATURESERVICE_SITE_SOURCE_TYPE = GROUP
    SAFE.ESRI-AGOL.ARCGISFEATURESERVICE_URL_TYPE = AGOL
    SAFE.ESRI-AGOL.ARCGISFEATURESERVICE_USE_SEARCH_ENVELOPE = NO
    SAFE.ESRI-AGOL.ARCGISFEATURESERVICE_VERIFY_HTTPS = WEB_CONN
    Faunacontrole -> AttributeManager_2
AttributeManager_2
    ATTR_TABLE:
      SET_TO Datum_Kapvergunning_aangevraagd (int64) = @Substring(@Value(Datum_Kapvergunning_aangevraagd),0,13)
      SET_TO Datum_Gerooid (int64) = @Substring(@Value(Datum_Gerooid),0,13)
      SET_TO Escalatiedatum_te_rooien (int64) = @Substring(@Value(Escalatiedatum_te_rooien),0,13)
      SET_TO KV_geldig_vanaf (int64) = @Substring(@Value(KV_geldig_vanaf),0,13)
      SET_TO CreationDate_1 (buffer) = @Substring(@Value(CreationDate_1),0,13)
      SET_TO EditDate_1 (int64) = @Substring(@Value(EditDate_1),0,13)
      SET_TO Editor_1 (varchar(128))
      SET_TO Dat_acc_rooi (int64) = @Substring(@Value(Dat_acc_rooi),0,13)
    -> Junction_3

Bookmark: ROOIEN
Junction_3
    -> ChangeDetector_rooien_2 [REVISED]
ChangeDetector_rooien_2
    BLANK_AND_MISSING_DIFFER = No
    CHECK_TYPES_AND_ENCODINGS = No
    MATCHATTRS = Aanwezig BEHEERDER BEHEEROBJECTOMSCHRIJVING Bewonend Boom_gerooid BOOMSORTIMENT BOOMSTATUS BRON BUURT Controleur_faunacheck Dat_acc_rooi Datum_Gerooid Datum_Kapvergunning_aangevraagd DIAMETER EditDate_1 Editor_1 EIGENAAR Escalatiedatum_te_rooien Gerooid_door GEVOLG GlobalID Holten_scheuren_gaten ID ID_MAATREGEL INSPECTIE_DATUM Kapvergunning_aangevraagd_door KV_geldig_vanaf Loshangende_schors MAATREGEL Nest_aanwezig OBJECTID OBJECTID_1 OBJECTID_2 ONDERHOUDSPLOEG Opmerking opmerking_uitvoering OPMERKINGEN PLAATSAANDUIDING Rooien SCHADE stam_omtrek Status_kapvergunning STRAAT Toelichting_Inspectie WIJK WOONPLAATS X Y
    MATCH_STRATEGY_LOOKUP = MATCH
    PREEMPTIVE_ATTRS = GlobalID
    UNCHANGED_OUTPUT_LOOKUP = ORIGINAL
    UPDATED_LIST_NAME = Wijzigingen
    UPSERT_MODE = No
    MATCH_STRATEGY = Match Selected Attributes
    UNCHANGED_OUTPUT = Output Original
    UPDATED -> ListExploder_3
    UPDATED -> FeatureWriter_Excel_Rooien [Updated]
    UPDATED -> StatisticsCalculator
    UPDATED -> Bomenrooien_Vastgoed_IOB (writer POSTGIS_1)
    INSERTED -> FeatureWriter_Excel_Rooien [Inserted]
    INSERTED -> StatisticsCalculator
    INSERTED -> Bomenrooien_Vastgoed_IOB (writer POSTGIS_1)
    DELETED -> FeatureWriter_Excel_Rooien [Deleted]
    DELETED -> StatisticsCalculator
    UNCHANGED -> FeatureWriter_Excel_Rooien [Unchanged]
    UNCHANGED -> StatisticsCalculator
FeatureWriter_Excel_Rooien
    CONFIG_PARAMETERS = ESCAPE_COMMAS_IN_FTP_FORMAT_PARAMETERS,no
    DATASET = @Value(ExcelRooienDoelPath)
    DATASET_ATTR = _dataset
    FEATURE_TYPE_LIST_ATTR = _feature_types
    FORMAT = XLSXW
    MORE_SUMMARY_ATTRS = DatumStamp VorigeWeeknummer
    TOTAL_FEATURES_WRITTEN_ATTR = _total_features_written
    XLSXW_ALWAYS_CREATE_FEATURE_TYPES = NO
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = NO
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = No
    XLSXW_WRITER_MODE = Insert
    SUMMARY -> ListExploder_7
ListExploder_7
    ATTR_CONFLICT_RES_LOOKUP = INCOMING_IF_CONFLICT
    INDEX_ATTR = _element_index
    LIST_ATTR = _feature_types{}
    ATTR_ACCUM_MODE = Merge List Attributes
    ATTR_CONFLICT_RES = Use List Attribute Values
    ELEMENTS -> AttributeFilter
AttributeFilter
    ATTR_NAME = name
    ATTR_VALUES = Statistiek,GerooideBomen,Wijzigingen,GewijzigdeBomen,NieuweBomen,VerwijderdeBomen,OngewijzigdeBomen,<Empty>,<Missing>,<Null>,<Unfiltered>
    Wijzigingen -> PythonCaller
    GewijzigdeBomen -> PythonCaller
    NieuweBomen -> PythonCaller
    VerwijderdeBomen -> PythonCaller
    OngewijzigdeBomen -> PythonCaller
PythonCaller
    INPUT_PORT_CONNECTED = CONNECTED
    PYTHONSOURCE:
      import fme
      from fme import BaseTransformer
      import fmeobjects


      class FeatureProcessor(BaseTransformer):
          """Template Class Interface:
          When using this class, make sure its name is set as the value of the 'Class to Process Features'
          transformer parameter.

          This class inherits from 'fme.BaseTransformer'. For full details of this class, its methods, and
          expected usage, see https://docs.safe.com/fme/html/fmepython/api/fme.html#fme.BaseTransformer.
          """

          def __init__(self):
              """Base constructor for class members."""
              pass

          def has_support_for(self, support_type: int):
              """This method is called by FME to determine if the PythonCaller supports Bulk mode,
              which allows for significant performance gains when processing large numbers of features.
              """
              return support_type == fmeobjects.FME_SUPPORT_FEATURE_TABLE_SHIM

          def input(self, feature: fmeobjects.FMEFeature):
              """This method is called for each feature which enters the PythonCaller."""
              xlsx_path = feature.getAttribute('_dataset')  # or r"C:\temp\out.xlsx"
              sheet_to_hide = feature.getAttribute('name')  # or "Sheet1"

              try:
                  import openpyxl
              except ImportError:
                  feature.setAttribute('python_error', 'openpyxl not installed in this FME Python environment')
                  self.pyoutput(feature)
                  return

              wb = openpyxl.load_workbook(xlsx_path)
              if sheet_to_hide in wb.sheetnames:
                  ws = wb[sheet_to_hide]
                  ws.sheet_state = 'hidden'   # use 'veryHidden' if you want it not unhideable via Excel UI
                  wb.save(xlsx_path)
                  feature.setAttribute('sheet_hidden', sheet_to_hide)
              else:
                  feature.setAttribute('python_error', f'Sheet not found: {sheet_to_hide}')

              self.pyoutput(feature, output_tag="PYOUTPUT")


          def close(self):
              """This method is called once all the FME Features have been processed from input()."""
              pass

          def process_group(self):
              """This method is called by FME for each group when group processing mode is enabled."""
              pass

          def reject_feature(self, feature: fmeobjects.FMEFeature, code: str, message: str):
              """This method can be used to output a feature to the <Rejected> port."""
              feature.setAttribute("fme_rejection_code", code)
              feature.setAttribute("fme_rejection_message", message)
              self.pyoutput(feature, output_tag="<Rejected>")
    PYTHONSYMBOL = FeatureProcessor
    -> DuplicateFilter

Bookmark: LEES Vastgoed database
FeatureReader
    ATTRIBUTES = public.Bomenrooien_Vastgoed_IOB,"Aanwezig,Nest_aanwezig,Holten_scheuren_gaten,Loshangende_schors,Rooien,Opmerking,OBJECTID,BEHEEROBJECTOMSCHRIJVING,BOOMSORTIMENT,BUURT,DIAMETER,ID,STRAAT,WIJK,WOONPLAATS,MAATREGEL,INSPECTIE_DATUM,OBJECTID_1,CreationDate,Creator,EditDate,Editor,BRON,ID_MAATREGEL,Controleur_faunacheck,Datum_Kapvergunning_aangevraagd,Kapvergunning_aangevraagd_door,Datum_Gerooid,Escalatiedatum_te_rooien,Gerooid_door,OBJECTID_2,Status_kapvergunning,Boom_gerooid,opmerking_uitvoering,KV_geldig_vanaf,SCHADE,Toelichting_Inspectie,GlobalID,CreationDate_1,Creator_1,EditDate_1,Editor_1,BEHEERDER,Dat_acc_rooi,BOOMSTATUS,OPMERKINGEN,EIGENAAR,X,Y,stam_omtrek,PLAATSAANDUIDING,GEVOLG,Bewonend,ONDERHOUDSPLOEG,arcgisfeatureservice_feature_url",public.Bomensnoei_Vastgoed_IOB,"OBJECTID,BEHEEROBJECTOMSCHRIJVING,BOOMSORTIMENT,BUURT,ID,STRAAT,WIJK,WOONPLAATS,MAATREGEL,ID_MAATREGEL,SCHADE,OPMERKINGEN,Uitgevoerd_door,UITVOERDER,Status,RedenNietGesnoeid,Datum_uitgevoerd,HOOGTE,TAKVRIJE_ZONE,Opmerking_uitvoering,RedenAfkeuring,MaatregelToegevoegd,PLANDATUM,CreationDate,Creator,EditDate,Editor,BEHEERDER,EIGENAAR,ONDERHOUDSPLICHTIGE,BOOMBEELD,GlobalID"
    ATTR_ACCUM_MODE = Merge Initiator and Result
    ATTR_CONFLICT_RES = Use Result
    ATTR_IGNORE_NULLS = No
    CLIP_TO_ENVELOPE = NO
    COMBINE_GEOM = Use Result
    DATASET = FME-PostGIS-Vastgoed
    FEATURETYPES = public.Bomenrooien_Vastgoed_IOB public.Bomensnoei_Vastgoed_IOB
    FORMAT = POSTGIS
    GEOMETRY_TYPES = public.Bomenrooien_Vastgoed_IOB,"""geom,fme_area,fme_collection,fme_line,fme_point,fme_surface""",public.Bomensnoei_Vastgoed_IOB,"""geom,fme_area,fme_collection,fme_line,fme_point,fme_surface"""
    INITIATOR_FIRST_OUTPUT = default
    INPUT_PORT_INITIATOR_CONNECTED = CONNECTED
    INTERACT = NONE
    ORDER_RESULTS = No
    OUTPUT_ADD_SCHEMA_ATTRIBUTES = NO
    OUTPUT_FEATURES_DISPLAY = Schema and Data Features
    OUTPUT_USE_SCHEMA_CACHE = YES
    POSTGIS_CREATE_FEATURE_TABLES_FROM_DATA = Yes
    POSTGIS_DISABLE_COLLECTION_SPLITTING = yes
    POSTGIS_FEATURES_PER_FETCH = 10000
    POSTGIS_NAMED_CONNECTION = FME-PostGIS-Vastgoed
    POSTGIS_QUERY_FEATURE_TYPES_FOR_MERGE_FILTERS = Yes
    POSTGIS_READ_TIME_WITH_TIMEZONE = Yes
    POSTGIS_SCHEMAS_FOR_TABLE_LISTING = public
    POSTGIS_USE_SEARCH_ENVELOPE = NO
    POSTGIS_USE_TRUE_POSTGIS_TYPES = yes
    READER_BEHAVIOR = SELECTFEATTYPES
    public.Bomenrooien_Vastgoed_IOB -> ChangeDetector_rooien_2 [ORIGINAL]
    public.Bomensnoei_Vastgoed_IOB -> ChangeDetector_snoei_2 [ORIGINAL]

Bookmark: Verwerk gewijzigde velden rooien
ListExploder_3
    ATTR_CONFLICT_RES_LOOKUP = INCOMING_IF_CONFLICT
    INDEX_ATTR = _element_index
    LIST_ATTR = Wijzigingen{}
    ATTR_ACCUM_MODE = Merge List Attributes
    ATTR_CONFLICT_RES = Use List Attribute Values
    ELEMENTS -> TestFilter_statusveld
TestFilter_statusveld
    DEFAULT_VALUE = <UNFILTERED>
    PASSED_TEST_GROUP_OUTPUT = FIRST
    TEST_LIST = "BOOL_OP,OR,COMPOSITE_TEST,""""""1"""""",TEST_CLAUSE,TEST @Value(attributeName) = Boom_gerooid",@Value(Boom_gerooid) is gewijzigd
    @Value(Boom_gerooid) is gewijzigd -> AttributeKeeper_wijzigingen_3
    @Value(Boom_gerooid) is gewijzigd -> AttributeKeeper_gerooide_bomen
    <UNFILTERED> -> AttributeKeeper_wijzigingen_3
AttributeKeeper_gerooide_bomen
    CREATE_BULK_MODE_FEATURES = NO
    KEEP_ATTRS = BEHEEROBJECTOMSCHRIJVING,Aanwezig,BEHEERDER,Bewonend,Boom_gerooid,BOOMSORTIMENT,BOOMSTATUS,BRON,BUURT,Controleur_faunacheck,Dat_acc_rooi,Datum_Gerooid,Datum_Kapvergunning_aangevraagd,DatumStamp,DIAMETER,EIGENAAR,Escalatiedatum_te_rooien,Gerooid_door,GEVOLG,GlobalID,Holten_scheuren_gaten,ID,ID_MAATREGEL,INSPECTIE_DATUM,Kapvergunning_aangevraagd_door,KV_geldig_vanaf,Loshangende_schors,MAATREGEL,Nest_aanwezig,OBJECTID,OBJECTID_1,OBJECTID_2,ONDERHOUDSPLOEG,Opmerking,opmerking_uitvoering,OPMERKINGEN,PLAATSAANDUIDING,Rooien,SCHADE,stam_omtrek,Status_kapvergunning,STRAAT,Toelichting_Inspectie,WIJK,WOONPLAATS,X,Y,ExcelRooienDoelPath
    -> DateTimeConverter_4
DateTimeConverter_4
    DATETIME_ATTR = Datum_Gerooid
    IN_FORMAT = %Y%m%d%H%M
    OUT_FORMAT = %d-%m-%Y
    PASSTHROUGH = YES
    REPAIR_INPUT = YES
    -> FeatureWriter_Excel_Rooien [Output00]
    -> StatisticsCalculator_2
AttributeKeeper_wijzigingen_3
    CREATE_BULK_MODE_FEATURES = NO
    KEEP_ATTRS = action,attributeName,BEHEEROBJECTOMSCHRIJVING,originalValue,revisedValue,ExcelRooienDoelPath,xlsx_sheet_visible
    -> FeatureWriter_Excel_Rooien [Output]

Bookmark: Aantal gerooid naar statistiek
StatisticsCalculator_2
    ATTR_ACCUM_MODE = None
    CALCULATION_MODE = NUMERIC
    FEAT_STATS = GlobalID,NUMERIC_MODE,,,COUNT,,,,,,,,,,
    GROUP_BY = ExcelRooienDoelPath
    SUMMARY -> AttributeManager_5
AttributeManager_5
    ATTR_TABLE:
      RENAME_SET_VALUE GlobalID.total_count > Aantal (uint64)
      SET_TO Status (varchar(7)) = Gerooid
    -> NoFeaturesTester_2
NoFeaturesTester_2
    NoInput -> FeatureMerger_4 [REQUESTOR]
    -> FeatureWriter_Excel_Rooien [Merged]
FeatureMerger_4
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeManager_11
AttributeManager_11
    ATTR_TABLE:
      SET_TO Aantal (uint64) = 0
      SET_TO Status (varchar(20)) = Geen bomen gerooid !
    USER_EXPOSED_ATTRIBUTES = GlobalID.total_count
    -> FeatureWriter_Excel_Rooien [Merged]

Bookmark: Statstiek maken
StatisticsCalculator
    ATTR_ACCUM_MODE = None
    CALCULATION_MODE = NUMERIC
    FEAT_STATS = GlobalID,NUMERIC_MODE,,,COUNT,,,,,,,,,,
    GROUP_BY = fme_db_operation ExcelRooienDoelPath
    SUMMARY -> AttributeManager
AttributeManager
    ATTR_TABLE:
      RENAME_SET_VALUE fme_db_operation > Status (char(9)) = FME_CONDITIONAL:DEFAULT_VALUE'_FME_NO_OP_'BOOL_OP;OR;COMPOSITE_TEST;1;TEST Status ATTRIBUTE_IS_MISSING _FME_BLANK_STRING_'Ongewijzigd'FME_NUM_CONDITIONS2___
      RENAME_SET_VALUE GlobalID.total_count > Aantal (uint64)
    -> AttributeValueMapper
AttributeValueMapper
    DEFAULT_VALUE = Ongewijzigd
    LUT = UPDATE,Gewijzigd,DELETE,Verwijderd,INSERT,Toegevoegd
    MAPPING_DIRECTION = FORWARD
    SRC = Status
    VAL_ATTR = Status
    -> FeatureMerger [SUPPLIER]
FeatureMerger
    ATTR_ACCUM_MODE = Merge Supplier
    ATTR_CONFLICT_RES_LOOKUP = SUPPLIER_IF_CONFLICT
    IGNORE_NULLS = No
    JOIN_KEYS = @Value(Status) @Value(Status) AUTO
    MERGE_TYPE_VAL = ATTRIBUTES
    PROCESS_DUPS = NO
    REJECT_NULL_MISSING_KEYS = No
    SUPPLIERS_FIRST = No
    ATTR_CONFLICT_RES = Use Supplier
    MERGE_TYPE = Attributes Only

Bookmark: WRITE PostGIS database
Bomenrooien_Vastgoed_IOB (writer POSTGIS_1)
    attributes: Aanwezig varchar(50), Nest_aanwezig varchar(50), Holten_scheuren_gaten varchar(50), Loshangende_schors varchar(50), Rooien varchar(50), Opmerking varchar(200), OBJECTID varchar(200), BEHEEROBJECTOMSCHRIJVING varchar(50), BOOMSORTIMENT varchar(100), BUURT varchar(50), DIAMETER int4, ID int4, STRAAT varchar(50), WIJK varchar(50), WOONPLAATS varchar(50), MAATREGEL varchar(100), INSPECTIE_DATUM int8, OBJECTID_1 int4, CreationDate int8, Creator varchar(128), EditDate int8, Editor varchar(128), BRON varchar(50), ID_MAATREGEL varchar(200), Controleur_faunacheck varchar(50), Datum_Kapvergunning_aangevraagd int8, Kapvergunning_aangevraagd_door varchar(50), Datum_Gerooid int8, Escalatiedatum_te_rooien int8, Gerooid_door varchar(50),
      OBJECTID_2 int4, Status_kapvergunning varchar(50), Boom_gerooid varchar(20), opmerking_uitvoering varchar(256), KV_geldig_vanaf int8, SCHADE varchar(256), Toelichting_Inspectie varchar(256), GlobalID varchar(38), CreationDate_1 varchar, Creator_1 varchar(128), EditDate_1 int8, Editor_1 varchar(128), BEHEERDER varchar(50), Dat_acc_rooi int8, BOOMSTATUS varchar(50), OPMERKINGEN varchar(256), EIGENAAR varchar(60), X varchar(10), Y varchar(10), stam_omtrek int4, PLAATSAANDUIDING varchar(10), GEVOLG varchar(50), Bewonend varchar(15), ONDERHOUDSPLOEG varchar(50)
Bomensnoei_Vastgoed_IOB (writer POSTGIS_3)
    attributes: OBJECTID int4, BEHEEROBJECTOMSCHRIJVING varchar(50), BOOMSORTIMENT varchar(100), BUURT varchar(50), ID int4, STRAAT varchar(50), WIJK varchar(50), WOONPLAATS varchar(50), MAATREGEL varchar(100), ID_MAATREGEL varchar(200), SCHADE varchar(256), OPMERKINGEN varchar(200), Uitgevoerd_door varchar(200), UITVOERDER varchar(256), Status varchar(256), RedenNietGesnoeid varchar(256), Datum_uitgevoerd int8, HOOGTE varchar(25), TAKVRIJE_ZONE varchar(60), Opmerking_uitvoering varchar(500), RedenAfkeuring varchar(256), MaatregelToegevoegd varchar(256), PLANDATUM int8, CreationDate int8, Creator varchar(128), EditDate int8, Editor varchar(128), BEHEERDER varchar(60), EIGENAAR varchar(60), ONDERHOUDSPLICHTIGE varchar(50),
      BOOMBEELD varchar(25), GlobalID varchar(38)

Bookmark: Productie cycle
Note: GITHUB test
DuplicateFilter
    INPUT_ORDERED_CHOICE_LOOKUP = NO
    KEYATTR = _dataset
    INPUT_ORDERED_CHOICE = No
    UNIQUE -> GKB_EmailGenerator
DuplicateFilter_2
    INPUT_ORDERED_CHOICE_LOOKUP = NO
    KEYATTR = _dataset
    INPUT_ORDERED_CHOICE = No
    UNIQUE -> GKB_EmailGenerator
GKB_EmailGenerator
    ATTACHMENT = @Value(_dataset)
    Body = Aan WVB, <br><br><br>De wekelijkse gegevenscheck op wijzigingen voor week @Value(VorigeWeeknummer).<br><br> UWVG GegevensCheck Rooien&Snoeien @Value(DatumStamp) <br> <br><br> Met vriendelijke groet,
    CC = dirkjan@gkbgroep.nl
    Subject = UWVG GegevensCheck WEEK @Value(VorigeWeeknummer)  Rooien&Snoeien @Value(DatumStamp)
    To = $(EMAIL_TO)
    VERZAMEL_MAIL = YES

Bookmark: "https://services.arcgis.com/zP1tGdLpGvt2qNJ6/arcgis/rest/services/Bomensnoei_vastgoed/FeatureServer/0"
FeatureReader_2
    ATTRIBUTES = Bomensnoei_Vastgoed_IOB,"OBJECTID,BEHEEROBJECTOMSCHRIJVING,BOOMSORTIMENT,BUURT,ID,STRAAT,WIJK,WOONPLAATS,MAATREGEL,ID_MAATREGEL,SCHADE,OPMERKINGEN,Uitgevoerd_door,UITVOERDER,Status,RedenNietGesnoeid,Datum_uitgevoerd,HOOGTE,TAKVRIJE_ZONE,Opmerking_uitvoering,RedenAfkeuring,MaatregelToegevoegd,PLANDATUM,CreationDate,Creator,EditDate,Editor,BEHEERDER,EIGENAAR,ONDERHOUDSPLICHTIGE,BOOMBEELD,GlobalID"
    ATTR_ACCUM_MODE = Merge Initiator and Result
    ATTR_CONFLICT_RES = Use Result
    ATTR_IGNORE_NULLS = No
    CLIP_TO_ENVELOPE = NO
    COMBINE_GEOM = Use Result
    COORDSYS = Netherlands-RDNew-2008
    FEATURETYPES = Bomensnoei_Vastgoed_IOB
    FORMAT = SAFE.ESRI-AGOL.ARCGISFEATURESERVICE
    GEOMETRY_TYPES = Bomensnoei_Vastgoed_IOB,""",fme_point"""
    INITIATOR_FIRST_OUTPUT = default
    INPUT_PORT_INITIATOR_CONNECTED = CONNECTED
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    SAFE.ESRI-AGOL.ARCGISFEATURESERVICE_AGOL_AUTH_NC = Esri ArcGIS Online (gisadmin_GKB)
    SAFE.ESRI-AGOL.ARCGISFEATURESERVICE_ALIAS_MODE = NONE
    SAFE.ESRI-AGOL.ARCGISFEATURESERVICE_COORDINATE_SYSTEM = Netherlands-RDNew-2008
    SAFE.ESRI-AGOL.ARCGISFEATURESERVICE_CREATE_FEATURE_TABLES_FROM_DATA = Yes
    SAFE.ESRI-AGOL.ARCGISFEATURESERVICE_FEATURES_PER_REQUEST = 1000
    SAFE.ESRI-AGOL.ARCGISFEATURESERVICE_FEATURE_SERVICE_WITH_ID = Bomensnoei_Vastgoed_IOB(92982e0df891477491e177eeaca5f733)
    SAFE.ESRI-AGOL.ARCGISFEATURESERVICE_FORMAT_DATETIME = FME_FORMAT
    SAFE.ESRI-AGOL.ARCGISFEATURESERVICE_FORMAT_GLOBALID = NO_FORMAT
    SAFE.ESRI-AGOL.ARCGISFEATURESERVICE_GROUP_ID = 9ffcaef4941d4fa48e8ef34e6a3acad1
    SAFE.ESRI-AGOL.ARCGISFEATURESERVICE_QUERY_FEATURE_TYPES_FOR_MERGE_FILTERS = Yes
    SAFE.ESRI-AGOL.ARCGISFEATURESERVICE_RESOLVE_DOMAINS = NO
    SAFE.ESRI-AGOL.ARCGISFEATURESERVICE_SITE_SOURCE_TYPE = GROUP
    SAFE.ESRI-AGOL.ARCGISFEATURESERVICE_URL_TYPE = AGOL
    SAFE.ESRI-AGOL.ARCGISFEATURESERVICE_USE_SEARCH_ENVELOPE = NO
    SAFE.ESRI-AGOL.ARCGISFEATURESERVICE_VERIFY_HTTPS = WEB_CONN
    Bomensnoei_Vastgoed_IOB -> AttributeManager_4
AttributeManager_4
    ATTR_TABLE:
      SET_TO CreationDate (int64) = @Substring(@Value(CreationDate),0,13)
      SET_TO EditDate (int64) = @Substring(@Value(EditDate),0,13)
      SET_TO Datum_uitgevoerd (int64) = @Substring(@Value(Datum_uitgevoerd),0,13)
    -> Junction_4

Bookmark: SNOEIEN
Junction_4
    -> ChangeDetector_snoei_2 [REVISED]
ChangeDetector_snoei_2
    BLANK_AND_MISSING_DIFFER = No
    CHECK_TYPES_AND_ENCODINGS = No
    MATCHATTRS = GlobalID BEHEERDER BEHEEROBJECTOMSCHRIJVING BOOMBEELD BOOMSORTIMENT BUURT Datum_uitgevoerd EditDate Editor EIGENAAR HOOGTE ID ID_MAATREGEL MAATREGEL MaatregelToegevoegd OBJECTID ONDERHOUDSPLICHTIGE Opmerking_uitvoering OPMERKINGEN PLANDATUM RedenAfkeuring RedenNietGesnoeid SCHADE Status STRAAT TAKVRIJE_ZONE Uitgevoerd_door UITVOERDER WIJK WOONPLAATS
    MATCH_STRATEGY_LOOKUP = MATCH
    PREEMPTIVE_ATTRS = GlobalID
    UNCHANGED_OUTPUT_LOOKUP = ORIGINAL
    UPDATED_LIST_NAME = Wijzigingen
    UPSERT_MODE = No
    MATCH_STRATEGY = Match Selected Attributes
    UNCHANGED_OUTPUT = Output Original
    UPDATED -> ListExploder_4
    UPDATED -> FeatureWriter_Excel_Snoeien [Updated]
    UPDATED -> StatisticsCalculator_3
    UPDATED -> Bomensnoei_Vastgoed_IOB (writer POSTGIS_3)
    INSERTED -> FeatureWriter_Excel_Snoeien [Inserted]
    INSERTED -> StatisticsCalculator_3
    INSERTED -> Bomensnoei_Vastgoed_IOB (writer POSTGIS_3)
    DELETED -> FeatureWriter_Excel_Snoeien [Deleted]
    DELETED -> StatisticsCalculator_3
    UNCHANGED -> FeatureWriter_Excel_Snoeien [Unchanged]
    UNCHANGED -> StatisticsCalculator_3
NoFeaturesTester
    NoInput -> FeatureMerger_3 [REQUESTOR]
    -> FeatureWriter_Excel_Snoeien [Merged]
FeatureMerger_3
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeManager_10
AttributeManager_10
    ATTR_TABLE:
      SET_TO Aantal (uint64) = 0
      SET_TO Status (varchar(8)) = Geen
      SET_TO MAATREGEL (varchar(100)) = Bomen gesnoeid
    USER_EXPOSED_ATTRIBUTES = GlobalID.total_count
    -> FeatureWriter_Excel_Snoeien [Merged]
FeatureWriter_Excel_Snoeien
    CONFIG_PARAMETERS = ESCAPE_COMMAS_IN_FTP_FORMAT_PARAMETERS,no
    DATASET = @Value(ExcelSnoeienDoelPath)
    DATASET_ATTR = _dataset
    FEATURE_TYPE_LIST_ATTR = _feature_types
    FORMAT = XLSXW
    MORE_SUMMARY_ATTRS = VorigeWeeknummer DatumStamp
    TOTAL_FEATURES_WRITTEN_ATTR = _total_features_written
    XLSXW_ALWAYS_CREATE_FEATURE_TYPES = NO
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = NO
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = No
    XLSXW_WRITER_MODE = Insert
    SUMMARY -> ListExploder_8
ListExploder_8
    ATTR_CONFLICT_RES_LOOKUP = INCOMING_IF_CONFLICT
    INDEX_ATTR = _element_index
    LIST_ATTR = _feature_types{}
    ATTR_ACCUM_MODE = Merge List Attributes
    ATTR_CONFLICT_RES = Use List Attribute Values
    ELEMENTS -> AttributeFilter_2
AttributeFilter_2
    ATTR_NAME = name
    ATTR_VALUES = Statistiek,GesnoeideBomen,Wijzigingen,GewijzigdeBomen,ToegevoegdeBomen,VerwijderdeBomen,OngewijzigdeBomen,<Empty>,<Missing>,<Null>,<Unfiltered>
    Wijzigingen -> PythonCaller_PythonCaller_Hide_worksheets
    GewijzigdeBomen -> PythonCaller_PythonCaller_Hide_worksheets
    ToegevoegdeBomen -> PythonCaller_PythonCaller_Hide_worksheets
    VerwijderdeBomen -> PythonCaller_PythonCaller_Hide_worksheets
    OngewijzigdeBomen -> PythonCaller_PythonCaller_Hide_worksheets

Bookmark: Verwerk gewijzigde velden snoeien
ListExploder_4
    ATTR_CONFLICT_RES_LOOKUP = INCOMING_IF_CONFLICT
    INDEX_ATTR = _element_index
    LIST_ATTR = Wijzigingen{}
    ATTR_ACCUM_MODE = Merge List Attributes
    ATTR_CONFLICT_RES = Use List Attribute Values
    ELEMENTS -> TestFilter_statusveld_2
TestFilter_statusveld_2
    DEFAULT_VALUE = <UNFILTERED>
    PASSED_TEST_GROUP_OUTPUT = FIRST
    TEST_LIST:
      "BOOL_OP,AND,COMPOSITE_TEST,""""""1 AND 2"""""",TEST_CLAUSE,TEST @Value(attributeName) = Status
      TEST @Value(revisedValue) = Gesnoeid",@Value(Status) is gewijzigd
    @Value(Status) is gewijzigd -> AttributeKeeper_wijzigingen_4
    @Value(Status) is gewijzigd -> AttributeKeeper_gesnoeide_bomen_2
    <UNFILTERED> -> AttributeKeeper_wijzigingen_4
AttributeKeeper_gesnoeide_bomen_2
    CREATE_BULK_MODE_FEATURES = NO
    KEEP_ATTRS = BEHEERDER,BEHEEROBJECTOMSCHRIJVING,BOOMBEELD,BOOMSORTIMENT,BUURT,Datum_uitgevoerd,EIGENAAR,GlobalID,HOOGTE,ID,ID_MAATREGEL,MAATREGEL,MaatregelToegevoegd,OBJECTID,ONDERHOUDSPLICHTIGE,Opmerking_uitvoering,OPMERKINGEN,PLANDATUM,RedenAfkeuring,RedenNietGesnoeid,SCHADE,Status,STRAAT,TAKVRIJE_ZONE,Uitgevoerd_door,UITVOERDER,WIJK,WOONPLAATS,ExcelSnoeienDoelPath
    -> DateTimeConverter_5
DateTimeConverter_5
    DATETIME_ATTR = Datum_uitgevoerd
    IN_FORMAT = %Y%m%d%H%M
    OUT_FORMAT = %d-%m-%Y
    PASSTHROUGH = YES
    REPAIR_INPUT = YES
    -> FeatureWriter_Excel_Snoeien [Output00]
    -> StatisticsCalculator_4
AttributeKeeper_wijzigingen_4
    CREATE_BULK_MODE_FEATURES = NO
    KEEP_ATTRS = action,attributeName,BEHEEROBJECTOMSCHRIJVING,originalValue,revisedValue,ExcelSnoeienDoelPath
    -> FeatureWriter_Excel_Snoeien [Output]

Bookmark: Aantal gerooid naar statistiek
StatisticsCalculator_4
    ATTR_ACCUM_MODE = None
    CALCULATION_MODE = NUMERIC
    FEAT_STATS = GlobalID,NUMERIC_MODE,,,COUNT,,,,,,,,,,
    GROUP_BY = ExcelSnoeienDoelPath MAATREGEL
    SUMMARY -> AttributeManager_9
AttributeManager_9
    ATTR_TABLE:
      RENAME_SET_VALUE GlobalID.total_count > Aantal (uint64)
      SET_TO Status (varchar(8)) = Gesnoeid
    -> NoFeaturesTester

Bookmark: Statstiek maken
StatisticsCalculator_3
    ATTR_ACCUM_MODE = None
    CALCULATION_MODE = NUMERIC
    FEAT_STATS = GlobalID,NUMERIC_MODE,,,COUNT,,,,,,,,,,
    GROUP_BY = fme_db_operation ExcelRooienDoelPath MAATREGEL
    SUMMARY -> AttributeManager_8
AttributeManager_8
    ATTR_TABLE:
      RENAME_SET_VALUE fme_db_operation > Status (char(9)) = FME_CONDITIONAL:DEFAULT_VALUE'_FME_NO_OP_'BOOL_OP;OR;COMPOSITE_TEST;1;TEST Status ATTRIBUTE_IS_MISSING _FME_BLANK_STRING_'Ongewijzigd'FME_NUM_CONDITIONS2___
      RENAME_SET_VALUE GlobalID.total_count > Aantal (uint64)
    -> AttributeValueMapper_2
AttributeValueMapper_2
    DEFAULT_VALUE = Ongewijzigd
    LUT = UPDATE,Gewijzigd,DELETE,Verwijderd,INSERT,Toegevoegd
    MAPPING_DIRECTION = FORWARD
    SRC = Status
    VAL_ATTR = Status
    -> FeatureMerger_2 [SUPPLIER]
    -> FeatureMerger_2 [REQUESTOR]
FeatureMerger_2
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(Status) @Value(Status) AUTO
    MERGE_TYPE_VAL = ATTRIBUTES
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGE_TYPE = Attributes Only

Bookmark: DEVELOPMENT
SubstringExtractor [off]
    END = 13
    RESULT_ATTR = _substring
    SRC_STRING = @Value(CreationDate_1)
    START = 0
    -> AttributeManager_3 [off]
AttributeManager_3 [off]
Junction [off]
    -> ChangeDetector_rooien [REVISED] [off]
Junction_2 [off]
    -> ChangeDetector_snoei [REVISED] [off]
ChangeDetector_rooien [off]
    BLANK_AND_MISSING_DIFFER = No
    CHECK_TYPES_AND_ENCODINGS = No
    MATCHATTRS = Aanwezig BEHEERDER BEHEEROBJECTOMSCHRIJVING Bewonend Boom_gerooid BOOMSORTIMENT BOOMSTATUS BRON BUURT Controleur_faunacheck Dat_acc_rooi Datum_Gerooid Datum_Kapvergunning_aangevraagd DIAMETER EditDate_1 Editor_1 EIGENAAR Escalatiedatum_te_rooien Gerooid_door GEVOLG GlobalID Holten_scheuren_gaten ID ID_MAATREGEL INSPECTIE_DATUM Kapvergunning_aangevraagd_door KV_geldig_vanaf Loshangende_schors MAATREGEL Nest_aanwezig OBJECTID OBJECTID_1 OBJECTID_2 ONDERHOUDSPLOEG Opmerking opmerking_uitvoering OPMERKINGEN PLAATSAANDUIDING Rooien SCHADE stam_omtrek Status_kapvergunning STRAAT Toelichting_Inspectie WIJK WOONPLAATS X Y
    MATCH_STRATEGY_LOOKUP = MATCH
    PREEMPTIVE_ATTRS = GlobalID
    UNCHANGED_OUTPUT_LOOKUP = ORIGINAL
    UPDATED_LIST_NAME = Wijzigingen
    UPSERT_MODE = No
    MATCH_STRATEGY = Match Selected Attributes
    UNCHANGED_OUTPUT = Output Original
    UPDATED -> ListExploder [off]
    UPDATED -> FeatureWriter [Updated] [off]
    INSERTED -> FeatureWriter [Inserted] [off]
    DELETED -> FeatureWriter [Deleted] [off]
    UNCHANGED -> FeatureWriter [Unchanged] [off]
ListExploder [off]
    ATTR_CONFLICT_RES_LOOKUP = INCOMING_IF_CONFLICT
    INDEX_ATTR = _element_index
    LIST_ATTR = Wijzigingen{}
    ATTR_ACCUM_MODE = Merge List Attributes
    ATTR_CONFLICT_RES = Use List Attribute Values
    ELEMENTS -> AttributeKeeper_wijzigingen [off]
AttributeKeeper_wijzigingen [off]
    CREATE_BULK_MODE_FEATURES = NO
    KEEP_ATTRS = action,attributeName,BEHEEROBJECTOMSCHRIJVING,originalValue,revisedValue,EditDate_1,Editor_1
    -> DateTimeConverter_3 [off]
DateTimeConverter_3 [off]
    DATETIME_ATTR = EditDate_1
    IN_FORMAT = %Y%m%d%H%M
    OUT_FORMAT = %d-%m-%Y
    PASSTHROUGH = NO
    REPAIR_INPUT = YES
    -> FeatureWriter [Output] [off]
FeatureWriter [off]
    CONFIG_PARAMETERS = ESCAPE_COMMAS_IN_FTP_FORMAT_PARAMETERS,no
    DATASET = c:\temp\UWVG_Rooien.xlsx
    DATASET_ATTR = _dataset
    FEATURE_TYPE_LIST_ATTR = _feature_types
    FORMAT = XLSXW
    TOTAL_FEATURES_WRITTEN_ATTR = _total_features_written
    XLSXW_ALWAYS_CREATE_FEATURE_TYPES = NO
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = NO
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = No
    XLSXW_WRITER_MODE = Insert
ChangeDetector_snoei [off]
    BLANK_AND_MISSING_DIFFER = No
    CHECK_TYPES_AND_ENCODINGS = No
    MATCHATTRS = GlobalID BEHEERDER BEHEEROBJECTOMSCHRIJVING BOOMBEELD BOOMSORTIMENT BUURT Datum_uitgevoerd EditDate Editor EIGENAAR HOOGTE ID ID_MAATREGEL MAATREGEL MaatregelToegevoegd OBJECTID ONDERHOUDSPLICHTIGE Opmerking_uitvoering OPMERKINGEN PLANDATUM RedenAfkeuring RedenNietGesnoeid SCHADE Status STRAAT TAKVRIJE_ZONE Uitgevoerd_door UITVOERDER WIJK WOONPLAATS
    MATCH_STRATEGY_LOOKUP = MATCH
    PREEMPTIVE_ATTRS = GlobalID
    UNCHANGED_OUTPUT_LOOKUP = ORIGINAL
    UPDATED_LIST_NAME = Wijzigingen
    UPSERT_MODE = No
    MATCH_STRATEGY = Match Selected Attributes
    UNCHANGED_OUTPUT = Output Original
    UPDATED -> FeatureWriter_2 [Updated] [off]
    UPDATED -> ListExploder_2 [off]
    INSERTED -> FeatureWriter_2 [Inserted] [off]
    DELETED -> FeatureWriter_2 [Deleted] [off]
    UNCHANGED -> FeatureWriter_2 [Unchanged] [off]
ListExploder_2 [off]
    ATTR_CONFLICT_RES_LOOKUP = INCOMING_IF_CONFLICT
    INDEX_ATTR = _element_index
    LIST_ATTR = Wijzigingen{}
    ATTR_ACCUM_MODE = Merge List Attributes
    ATTR_CONFLICT_RES = Use List Attribute Values
    ELEMENTS -> AttributeKeeper_wijzigingen_2 [off]
AttributeKeeper_wijzigingen_2 [off]
    CREATE_BULK_MODE_FEATURES = NO
    KEEP_ATTRS = action,attributeName,BEHEEROBJECTOMSCHRIJVING,originalValue,revisedValue,EditDate,Editor
    -> DateTimeConverter_2 [off]
DateTimeConverter_2 [off]
    DATETIME_ATTR = EditDate
    IN_FORMAT = %Y%m%d%H%M
    OUT_FORMAT = %d-%m-%Y
    PASSTHROUGH = NO
    REPAIR_INPUT = YES
    -> FeatureWriter_2 [Output] [off]
FeatureWriter_2 [off]
    CONFIG_PARAMETERS = ESCAPE_COMMAS_IN_FTP_FORMAT_PARAMETERS,no
    DATASET = c:\temp\UWVG_Snoeien.xlsx
    DATASET_ATTR = _dataset
    FEATURE_TYPE_LIST_ATTR = _feature_types
    FORMAT = XLSXW
    TOTAL_FEATURES_WRITTEN_ATTR = _total_features_written
    XLSXW_ALWAYS_CREATE_FEATURE_TYPES = NO
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = NO
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = No
    XLSXW_WRITER_MODE = Insert
DateTimeConverter [off]
    DATETIME_ATTR = CreationDate_1
    OUT_FORMAT = FME
    PASSTHROUGH = NO
    REPAIR_INPUT = YES

Bookmark: LEES Vastgoed database LOCAL
Bomenrooien_Vastgoed_IOB (reader POSTGIS_6) [off]
    attributes: Aanwezig varchar(50), Nest_aanwezig varchar(50), Holten_scheuren_gaten varchar(50), Loshangende_schors varchar(50), Rooien varchar(50), Opmerking varchar(200), OBJECTID varchar(200), BEHEEROBJECTOMSCHRIJVING varchar(50), BOOMSORTIMENT varchar(100), BUURT varchar(50), DIAMETER int4, ID int4, STRAAT varchar(50), WIJK varchar(50), WOONPLAATS varchar(50), MAATREGEL varchar(100), INSPECTIE_DATUM int8, OBJECTID_1 int4, CreationDate int8, Creator varchar(128), EditDate int8, Editor varchar(128), BRON varchar(50), ID_MAATREGEL varchar(200), Controleur_faunacheck varchar(50), Datum_Kapvergunning_aangevraagd int8, Kapvergunning_aangevraagd_door varchar(50), Datum_Gerooid int8, Escalatiedatum_te_rooien int8, Gerooid_door varchar(50),
      OBJECTID_2 int4, Status_kapvergunning varchar(50), Boom_gerooid varchar(20), opmerking_uitvoering varchar(256), KV_geldig_vanaf int8, SCHADE varchar(256), Toelichting_Inspectie varchar(256), GlobalID varchar(38), CreationDate_1 int8, Creator_1 varchar(128), EditDate_1 int8, Editor_1 varchar(128), BEHEERDER varchar(50), Dat_acc_rooi int8, BOOMSTATUS varchar(50), OPMERKINGEN varchar(256), EIGENAAR varchar(60), X varchar(10), Y varchar(10), stam_omtrek int4, PLAATSAANDUIDING varchar(10), GEVOLG varchar(50), Bewonend varchar(15), ONDERHOUDSPLOEG varchar(50), arcgisfeatureservice_feature_url varchar
    -> Junction [off]
Bomensnoei_Vastgoed_IOB (reader POSTGIS_6) [off]
    attributes: OBJECTID int4, BEHEEROBJECTOMSCHRIJVING varchar(50), BOOMSORTIMENT varchar(100), BUURT varchar(50), ID int4, STRAAT varchar(50), WIJK varchar(50), WOONPLAATS varchar(50), MAATREGEL varchar(100), ID_MAATREGEL varchar(200), SCHADE varchar(256), OPMERKINGEN varchar(200), Uitgevoerd_door varchar(200), UITVOERDER varchar(256), Status varchar(256), RedenNietGesnoeid varchar(256), Datum_uitgevoerd int8, HOOGTE varchar(25), TAKVRIJE_ZONE varchar(60), Opmerking_uitvoering varchar(500), RedenAfkeuring varchar(256), MaatregelToegevoegd varchar(256), PLANDATUM int8, CreationDate int8, Creator varchar(128), EditDate int8, Editor varchar(128), BEHEERDER varchar(60), EIGENAAR varchar(60), ONDERHOUDSPLICHTIGE varchar(50),
      BOOMBEELD varchar(25), GlobalID varchar(38)
    -> Junction_2 [off]

Bookmark: Original
Bomenrooien_Vastgoed_IOB1 (reader POSTGIS_7) [off]
    attributes: Aanwezig varchar(50), Nest_aanwezig varchar(50), Holten_scheuren_gaten varchar(50), Loshangende_schors varchar(50), Rooien varchar(50), Opmerking varchar(200), OBJECTID varchar(200), BEHEEROBJECTOMSCHRIJVING varchar(50), BOOMSORTIMENT varchar(100), BUURT varchar(50), DIAMETER int4, ID int4, STRAAT varchar(50), WIJK varchar(50), WOONPLAATS varchar(50), MAATREGEL varchar(100), INSPECTIE_DATUM int8, OBJECTID_1 int4, CreationDate int8, Creator varchar(128), EditDate int8, Editor varchar(128), BRON varchar(50), ID_MAATREGEL varchar(200), Controleur_faunacheck varchar(50), Datum_Kapvergunning_aangevraagd int8, Kapvergunning_aangevraagd_door varchar(50), Datum_Gerooid int8, Escalatiedatum_te_rooien int8, Gerooid_door varchar(50),
      OBJECTID_2 int4, Status_kapvergunning varchar(50), Boom_gerooid varchar(20), opmerking_uitvoering varchar(256), KV_geldig_vanaf int8, SCHADE varchar(256), Toelichting_Inspectie varchar(256), GlobalID varchar(38), CreationDate_1 varchar, Creator_1 varchar(128), EditDate_1 int8, Editor_1 varchar(128), BEHEERDER varchar(50), Dat_acc_rooi int8, BOOMSTATUS varchar(50), OPMERKINGEN varchar(256), EIGENAAR varchar(60), X varchar(10), Y varchar(10), stam_omtrek int4, PLAATSAANDUIDING varchar(10), GEVOLG varchar(50), Bewonend varchar(15), ONDERHOUDSPLOEG varchar(50)
    -> ChangeDetector_rooien [ORIGINAL] [off]
Bomensnoei_Vastgoed_IOB2 (reader POSTGIS_7) [off]
    attributes: OBJECTID int4, BEHEEROBJECTOMSCHRIJVING varchar(50), BOOMSORTIMENT varchar(100), BUURT varchar(50), ID int4, STRAAT varchar(50), WIJK varchar(50), WOONPLAATS varchar(50), MAATREGEL varchar(100), ID_MAATREGEL varchar(200), SCHADE varchar(256), OPMERKINGEN varchar(200), Uitgevoerd_door varchar(200), UITVOERDER varchar(256), Status varchar(256), RedenNietGesnoeid varchar(256), Datum_uitgevoerd int8, HOOGTE varchar(25), TAKVRIJE_ZONE varchar(60), Opmerking_uitvoering varchar(500), RedenAfkeuring varchar(256), MaatregelToegevoegd varchar(256), PLANDATUM int8, CreationDate int8, Creator varchar(128), EditDate int8, Editor varchar(128), BEHEERDER varchar(60), EIGENAAR varchar(60), ONDERHOUDSPLICHTIGE varchar(50),
      BOOMBEELD varchar(25), GlobalID varchar(38)
    -> ChangeDetector_snoei [ORIGINAL] [off]

Bookmark: WRITE PostGIS database LOCAL Test
Bomenrooien_Vastgoed_IOB1 (writer POSTGIS_4) [off]
    attributes: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
Bomensnoei_Vastgoed_IOB2 (writer POSTGIS_4) [off]
    attributes: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
